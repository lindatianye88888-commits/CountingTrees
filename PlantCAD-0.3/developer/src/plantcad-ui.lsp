;;; PlantCAD workbench state and drawing interaction.
(defun pl:ui-state (/ p opts units issue)
  (setq p (pl:current) units (pl:units)
    opts (pl:plot-options))
  (setq issue (cond ((not p) "已有边线可直接用“布置→灌木线自动识别面积并标注”；布置植物再选树种。")
    ((and (not (pl:no-size-kind-p (pl:get 'kind p))) (<= (pl:get 'crown p) 0)) "当前规格尚缺冠幅，点击“开始布置”直接补填。")
    ((not units) "请先确认底图单位和出图比例。")
    ((pl:layer-issue (pl:tree-layer p)) (strcat "植物布置：" (pl:layer-issue (pl:tree-layer p)) " 几何面积识别不受树木图层影响。"))
    ((and (pl:no-size-kind-p (pl:get 'kind p)) (<= (pl:get 'crown p) 0)) "草类无尺寸：点放使用示意符号；面积请用种植范围识别。")
    (T "点击“开始布置”选择方式；已算面积可直接填充或引线标注。")))
  (pl:ai-o (list (list "ok" T) (list "ui_version" "0.3-float-2")
    (list "name" (if p (pl:get 'name p) ""))
    (list "spec_no" (if p (pl:get 'spec_no p) ""))
    (list "kind" (if p (pl:get 'kind p) 0))
    (list "crown_m" (if p (pl:get 'crown p) 0.0))
    (list "dbh_cm" (if p (pl:get 'dbh p) 0.0))
    (list "caliper_cm" (if p (pl:get 'caliper p) 0.0))
    (list "diameter_mode" (if (and p (= (pl:get 'diameter_mode p) 1)) "caliper" "dbh"))
    (list "style" (if p (pl:get 'style p) 0))
    (list "block" (if p (pl:get 'block p) ""))
    (list "units_per_m" (if units units 0.0))
    (list "hint" issue) (list "last_error" (if pl:*failure* pl:*failure* "")))))

(defun pl:layer-issue (name / ed flags)
  (setq ed (tblsearch "LAYER" name) flags (if ed (cdr (assoc 70 ed)) 0))
  (cond ((not ed) (strcat "目标图层不存在：" name))
    ((/= 0 (logand flags 4)) (strcat "目标图层已锁定：" name "。请解锁后布置。"))
    ((/= 0 (logand flags 1)) (strcat "目标图层已冻结：" name "。请解冻后布置。"))
    ((< (cdr (assoc 62 ed)) 0) (strcat "目标图层已关闭：" name "。请打开后布置。"))
    (T nil)))

(defun pl:preview-lines (style width height / i a r cx cy radius points out first prev pt)
  (setq cx (/ width 2.0) cy (/ height 2.0) radius (* 0.4 (min width height))
    points nil i 0 out nil)
  (repeat 49
    (setq a (* 2.0 pi (/ i 48.0))
      r (if (= style 1) (- 1.0 (* 0.11 (- 1.0 (cos (* 8.0 a))))) 1.0)
      pt (list (fix (+ cx (* radius r (cos a)))) (fix (+ cy (* radius r (sin a))))))
    (if (= i 0) (setq first pt))
    (if (= i 48) (setq pt first))
    (if prev (setq out (append out (list (append prev pt)))))
    (setq prev pt i (1+ i))) out)

(defun pl:dialog-preview (value / style width height line)
  (setq style (atoi value) width (dimx_tile "symbol_preview") height (dimy_tile "symbol_preview"))
  (start_image "symbol_preview")
  (fill_image 0 0 width height -2)
  (foreach line (pl:preview-lines style width height)
    (vector_image (car line) (cadr line) (caddr line) (nth 3 line) 3))
  (end_image)
  (set_tile "preview_caption" (nth style '("圆圈树冠" "简笔树冠" "自定义图块（此处为范围示意）")))
  (mode_tile "block" (if (= style 2) 0 1))
  (mode_tile "base" (if (= style 2) 0 1)))

(defun pl:resolve-placement (p / result)
  (if (and (not (pl:no-size-kind-p (pl:get 'kind p))) (<= (pl:get 'crown p) 0))
    (progn
      (setq pl:*require-crown* T)
      (setq result (vl-catch-all-apply 'pl:edit-dialog (list p)))
      (setq pl:*require-crown* nil)
      (if (vl-catch-all-error-p result) (pl:fail (vl-catch-all-error-message result)))
      (if result
        (progn (pl:save-def result) (pl:db-put "CURRENT" (pl:get 'id result)) result) nil))
    p))

;;; A one-item .NET ResultBuffer is a one-item AutoLISP list, including points and handles.
(defun pl:native-value (value)
  (if (and (listp value) (= (length value) 1)) (car value) value))

(defun pl:point-value (value / point)
  (setq point (pl:native-value value))
  (if (and (listp point) (member (length point) '(2 3))
           (numberp (car point)) (numberp (cadr point))
           (or (= (length point) 2) (numberp (caddr point))))
    (if (= (length point) 2) (append point '(0.0)) point) nil))

(defun pl:pick-placement (p units / opts scale height result point)
  (if (and (boundp 'pl:*native-ui*) pl:*native-ui*)
    (progn
      (setq opts (pl:plot-options)
        scale (if (and (= (getvar "TILEMODE") 0) (= (getvar "CVPORT") 1)) 1.0 (pl:get 'scale opts))
        height (pl:paper-height (pl:get 'paper_height opts) scale units))
      (setq result (pl:preview-point (pl:block-name p) (pl:block-scale p units) height (pl:get 'name p)))
      (if (pl:native-value result)
        (if (setq point (pl:point-value result)) point
          (pl:fail "植物预览返回的坐标格式无效，请重新加载插件后再布置。")) nil))
    (getpoint "\n植物中心（回车结束）：")))

(defun pl:insert-symbol (p point scale / doc layer previous result obj entity)
  (setq point (pl:point-value point))
  (if (not point) (pl:fail "植物中心坐标无效，尚未插入图块。"))
  (setq doc (pl:doc) layer (pl:tree-layer p))
  (if (and (boundp 'pl:*native-ui*) pl:*native-ui*)
    (progn
      (setq result (pl:native-value (pl:native-insert (pl:block-name p) point scale layer)))
      (if (or (/= (type result) 'STR) (= result "")) (pl:fail "插入未返回有效图块句柄，请查看CAD命令记录。"))
      (setq entity (handent result))
      (if (not entity) (pl:fail "插入后未找到图块，请查看CAD命令记录。"))
      (vlax-ename->vla-object entity))
    (progn
      ;; Create on the target layer so a locked current base layer cannot block insertion.
      (setq previous (vla-get-ActiveLayer doc))
      (vla-put-ActiveLayer doc (vla-Item (vla-get-Layers doc) layer))
      (setq result (vl-catch-all-apply 'vla-InsertBlock
        (list (pl:space) (vlax-3d-point point) (pl:block-name p) scale scale scale 0.0)))
      (vla-put-ActiveLayer doc previous)
      (if (vl-catch-all-error-p result) (pl:fail (vl-catch-all-error-message result)))
      result)))

(defun pl:edit-current-work (/ p result)
  (setq p (pl:current))
  (if (not p) (pl:library-work)
    (if (setq result (pl:edit-project-dialog p))
      (progn (pl:save-project-spec result) (pl:db-put "CURRENT" (pl:get 'id result))))))

(defun c:PLANTCADEDITCURRENT () (pl:run 'pl:edit-current-work))
(defun c:PLANTCADSYMBOLPICK () (pl:run 'pl:edit-current-work))
(pl:register-command "PLEDITCURRENT" "PLANTCADEDITCURRENT")
(pl:register-command "PLSYMBOLPICK" "PLANTCADSYMBOLPICK")
(princ)

(defun pl:edit-instance-work (/ e p result pick)
  (setq e (if (and (boundp 'pl:*edit-handle*) pl:*edit-handle*) (handent pl:*edit-handle*) nil) pl:*edit-handle* nil)
  (if (not e) (if (setq pick (entsel "\n选择要编辑的CountingTrees（数树）植物：")) (setq e (car pick))))
  (if e
    (if (and (setq p (pl:plant e)) (pl:writable e))
      (if (setq result (pl:edit-dialog p))
        (progn
          (setq result (pl:instance-variant result))
          (pl:built-blocks)
          (if (pl:apply-plant e result)
            (progn
              (pl:save-def result) (pl:db-put "CURRENT" (pl:get 'id result))
              (pl:sync-labels) (pl:ai-refresh-tables)
              (princ (strcat "\n已更新所选植物：" (pl:get 'name result) " / " (pl:get 'spec_no result)
                "；其他植物的原规格保留。")))
            (pl:fail "未能修改植物，请检查单位、图层和冠幅。"))))
      (alert "请选择未锁定的CountingTrees（数树）植物图块。"))))
(defun c:PLANTCADEDITINSTANCE () (pl:run 'pl:edit-instance-work))
