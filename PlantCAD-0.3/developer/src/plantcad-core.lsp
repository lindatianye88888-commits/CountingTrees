;;; PlantCAD III - rules independent of CAD/DCL/COM.
(defun pl:get (key data) (cdr (assoc key data)))
(defun pl:put (key value data / old)
  (if (setq old (assoc key data)) (subst (cons key value) old data)
    (append data (list (cons key value)))))
(defun pl:trim (s) (vl-string-trim " \t\r\n" s))
(defun pl:normal-name (s) (strcase (pl:trim s)))
(defun pl:number-input (s / c dots digits valid)
  (setq s (pl:trim s) dots 0 digits 0 valid T)
  (foreach c (vl-string->list s)
    (cond ((and (>= c 48) (<= c 57)) (setq digits (1+ digits)))
      ((= c 46) (setq dots (1+ dots))) (T (setq valid nil))))
  (if (and valid (> digits 0) (<= dots 1)) (atof s) nil))
(defun pl:num (n / s)
  (if (or (null n) (<= n 0.0)) ""
    (progn (setq s (rtos n 2 6))
      (if (vl-string-search "." s)
        (setq s (vl-string-right-trim "." (vl-string-right-trim "0" s))))
      (if (= (substr s 1 1) ".") (setq s (strcat "0" s))) s)))
(defun pl:area-text (n / text dot)
  ;; DIMZIN may suppress trailing/leading zeroes even when RTOS precision is 2.
  (setq text (rtos n 2 2))
  (if (= (substr text 1 1) ".") (setq text (strcat "0" text)))
  (setq dot (vl-string-search "." text))
  (if dot
    (while (< (- (strlen text) dot 1) 2) (setq text (strcat text "0")))
    (setq text (strcat text ".00"))) text)
(defun pl:quantity-text (p n)
  (if (= (pl:get 'quantity_unit p) "平方米") (pl:area-text n) (pl:num n)))
(defun pl:plant-rank (p)
  (cond ((member (pl:get 'kind p) '(0 6)) 0) ((= (pl:get 'kind p) 3) 1) (T 2)))
(defun pl:sort-plant-records (records / result rank row)
  (foreach rank '(0 1 2)
    (foreach row records (if (= (pl:plant-rank (car row)) rank) (setq result (append result (list row)))))) result)
(defun pl:sort-count-rows (rows / result rank row)
  (foreach rank '(0 1 2)
    (foreach row rows (if (= (pl:plant-rank (cadr row)) rank) (setq result (append result (list row)))))) result)
(defun pl:empty-plant (id)
  (list (cons 'id id) (cons 'name "") (cons 'kind 0)
    (cons 'dbh 0.0) (cons 'caliper 0.0) (cons 'diameter_mode 0)
    (cons 'height 0.0) (cons 'crown 0.0)
    (cons 'factor 1.0) (cons 'style 0) (cons 'block "") (cons 'base 1.0)
    (cons 'fill_pattern "") (cons 'fill_scale 0.1) (cons 'fill_angle 0.0)
    (cons 'spec_no "") (cons 'species_id "") (cons 'quantity_unit "株")))
(defun pl:upgrade-plant (p / pair)
  ;; Merge only absent fields: legacy DWG snapshots retain all original values.
  (foreach pair (pl:empty-plant (pl:get 'id p))
    (if (not (assoc (car pair) p)) (setq p (append p (list pair))))) p)
(defun pl:plant-error (p / normalized)
  (setq normalized (pl:upgrade-plant p))
  (cond
    ((= (pl:trim (pl:get 'name normalized)) "") "请输入植物名称。")
    ((> (strlen (pl:get 'name normalized)) 80) "名称过长，请控制在40个汉字以内。")
    ((not (member (pl:get 'kind normalized) '(0 1 2 3 4 5 6))) "植物类别无效。")
    ((or (< (pl:get 'dbh normalized) 0) (< (pl:get 'caliper normalized) 0)
         (< (pl:get 'height normalized) 0) (< (pl:get 'crown normalized) 0))
      "规格不能为负数。")
    ((or (<= (pl:get 'fill_scale normalized) 0) (< (pl:get 'fill_angle normalized) 0) (>= (pl:get 'fill_angle normalized) 360)) "填充比例须大于0，角度范围为0至小于360度。")
    ((<= (pl:get 'factor normalized) 0) "显示系数必须大于0。")
    ((not (member (pl:get 'diameter_mode normalized) '(0 1))) "下行径值类型无效。")
    ((not (or (member (pl:get 'quantity_unit normalized) '("株" "丛"))
      (and (pl:area-kind-p (pl:get 'kind normalized)) (= (pl:get 'quantity_unit normalized) "平方米"))))
      "单株单位请选择株或丛；灌木地被等面积规格可用平方米。")
    ((not (member (pl:get 'style normalized) '(0 1 2))) "图例样式无效。")
    ((and (= (pl:get 'style normalized) 2) (= (pl:get 'block normalized) ""))
      "使用自定义图块时，请填写图块名称。")
    ((and (= (pl:get 'style normalized) 2) (<= (pl:get 'base normalized) 0))
      "自定义图块基准直径必须大于0。") (T nil)))
(defun pl:insert-error (p)
  (cond ((pl:plant-error p) (pl:plant-error p))
    ((= (pl:get 'quantity_unit p) "平方米") "面积规格请使用区域填充或面积标注；单株布置请先将计数单位改为株或丛。")
    ((and (not (pl:no-size-kind-p (pl:get 'kind p))) (<= (pl:get 'crown p) 0)) "布置前请输入实际冠幅，单位cm。") (T nil)))
(defun pl:display-crown (p)
  (if (and (pl:no-size-kind-p (pl:get 'kind p)) (<= (pl:get 'crown p) 0)) 0.15 (pl:get 'crown p)))
(defun pl:diameter (p units) (* (pl:display-crown p) (pl:get 'factor p) units))
(defun pl:block-scale (p units)
  (/ (pl:diameter p units) (if (= (pl:get 'style p) 2) (pl:get 'base p) 1.0)))
(defun pl:mtext-safe (s / out c)
  (setq out "")
  (foreach c (vl-string->list s)
    (if (member c '(92 123 125)) (setq out (strcat out "\\")))
    (setq out (strcat out (chr c)))) out)
(defun pl:diameter-value (p)
  (pl:get (if (= (pl:get 'diameter_mode (pl:upgrade-plant p)) 1) 'caliper 'dbh) p))
(defun pl:dbh-text (p prefix units / n)
  (setq n (pl:num (pl:diameter-value p)))
  (if (= n "") ""
    (strcat (if (= (pl:get 'diameter_mode p) 1)
              (nth prefix '("" "d" "d=")) (nth prefix '("" "D" "D=")))
      n (if units "cm" ""))))
(defun pl:spec-text (p / parts text pair n)
  (setq parts nil text "")
  (foreach pair '((dbh "D=" "cm") (caliper "d=" "cm") (height "H=" "cm") (crown "P=" "cm"))
    (setq n (pl:dimension-text (car pair) p))
    (if (and (/= n "") (/= n "——")) (setq parts (append parts (list (strcat (cadr pair) n (caddr pair)))))))
  (foreach n parts (setq text (strcat text (if (= text "") "" "  ") n))) text)
(defun pl:label-text (p opts / name lower)
  (setq name (pl:mtext-safe (if (= (pl:get 'mode opts) 3) (pl:get 'spec_no p) (pl:get 'name p))))
  (setq lower (cond ((= (pl:get 'mode opts) 1)
      (pl:dbh-text p (pl:get 'prefix opts) (= (pl:get 'units opts) 1)))
    ((= (pl:get 'mode opts) 2) (pl:spec-text p)) (T "")))
  (strcat name (if (= lower "") "" (strcat "\\P" lower))))
(defun pl:count-key (p / q)
  (setq q (pl:upgrade-plant p))
  ;; A numbered project specification is a separate schedule row.
  (list (pl:normal-name (pl:get 'name q)) (pl:get 'kind q)
    (pl:get 'dbh q) (pl:get 'caliper q) (pl:get 'height q) (pl:get 'crown q)
    (strcase (pl:get 'spec_no q)) (pl:get 'quantity_unit q)))
(defun pl:add-count (p rows / key row)
  (setq key (pl:count-key p) row (assoc key rows))
  (if row (subst (list key (cadr row) (1+ (caddr row))) row rows)
    (append rows (list (list key p 1)))))
(defun pl:csv-cell (s / out c)
  (setq out "\"")
  (foreach c (vl-string->list s)
    (if (= c 34) (setq out (strcat out "\"")))
    (setq out (strcat out (chr c)))) (strcat out "\""))
(defun pl:kind-name (k) (nth k (pl:kind-names)))
(defun pl:kind-names () '("乔木" "灌木/藤本" "花草/地被" "灌木球" "花境" "草坪" "竹类"))
(defun pl:area-kind-p (kind) (member kind '(1 2 4 5)))
(defun pl:no-size-kind-p (kind) (member kind '(2 4 5)))
(defun pl:category-names () '("常绿乔木" "落叶/半落叶乔木" "常绿灌木" "落叶/半落叶灌木" "花卉地被" "观赏草" "竹类" "藤本" "水生植物" "棕榈类" "灌木球" "花境" "草坪"))
(defun pl:species-kind (category)
  (cond ((= category 10) 3) ((= category 11) 4) ((= category 12) 5)
    ((= category 6) 6) ((member category '(0 1 9)) 0) ((member category '(2 3 7)) 1) (T 2)))
(defun pl:default-plot-options () '((scale . 100.0) (paper_height . 10.0) (show_number . 0)))
(defun pl:plot-options (/ opts pair)
  ;; Stored paper height is mm; the settings dialog displays cm (10 mm = 1 cm).
  ;; Retain all saved values, including partially populated legacy settings.
  (setq opts (pl:db-get "PLOT_OPTIONS" nil))
  (foreach pair (pl:default-plot-options)
    (if (not (assoc (car pair) opts)) (setq opts (append opts (list pair))))) opts)
(defun pl:paper-height (paper_mm scale units) (/ (* paper_mm scale units) 1000.0))
(defun pl:spec-conflict (p defs / result row no)
  (setq no (strcase (pl:trim (pl:get 'spec_no (pl:upgrade-plant p)))))
  (foreach row defs
    (if (and (/= (pl:get 'id row) (pl:get 'id p))
             (= no (strcase (pl:get 'spec_no (pl:upgrade-plant row)))))
      (setq result T))) result)
(defun pl:next-spec-number (defs / n no used row)
  (setq n 1 used nil)
  (foreach row defs (setq used (cons (strcase (pl:get 'spec_no (pl:upgrade-plant row))) used)))
  (setq no "P001")
  (while (member no used)
    (setq n (1+ n) no (strcat "P" (if (< n 10) "00" (if (< n 100) "0" "")) (itoa n))))
  no)
(defun pl:spec-error (p defs / no)
  (setq no (pl:get 'spec_no p))
  (cond ((or (not no) (= (pl:trim no) "")) "请填写规格编号。")
    ((> (strlen no) 40) "规格编号最长40个字符。")
    ((or (vl-string-search "\t" no) (vl-string-search "\n" no)
         (vl-string-search "\r" no)) "规格编号不能包含换行或制表符。")
    ((pl:spec-conflict p defs) "当前项目已有此规格编号，请更换。") (T nil)))
(defun pl:species-filter (rows category query region / result row matches)
  (setq query (strcase (pl:trim query)) region (strcase (pl:trim region)))
  (foreach row rows
    (setq matches (or (< category 0) (= category (pl:get 'category row))
      (and (= category 10) (member (pl:get 'category row) '(2 3)))
      (and (= category 11) (member (pl:get 'category row) '(4 5 8)))
      (and (= category 12) (member (pl:get 'category row) '(4 5)))))
    (if (and matches
             (or (= query "") (vl-string-search query (strcase (pl:get 'name row))))
             (or (= region "") (vl-string-search region (strcase (pl:get 'region row)))))
      (progn
        (if (>= category 10) (setq row (pl:put 'placement_kind (pl:species-kind category) row)))
        (setq result (append result (list row)))))) result)
(defun pl:split-tab (s / result part c)
  (setq result nil part "")
  (foreach c (vl-string->list s)
    (if (= c 9) (setq result (append result (list part)) part "")
      (setq part (strcat part (chr c)))))
  (append result (list part)))
(defun pl:species-error (s / msg key value)
  (setq msg nil)
  (foreach key '(id name region source note supply)
    (setq value (pl:get key s))
    (if (or (not value) (vl-string-search "\t" value)
            (vl-string-search "\n" value) (vl-string-search "\r" value))
      (setq msg "字段不能包含制表符或换行。")))
  (cond (msg msg)
    ((or (= (pl:trim (pl:get 'id s)) "") (= (pl:trim (pl:get 'name s)) ""))
      "品种ID与名称不能为空。")
    ((> (strlen (pl:get 'name s)) 80) "植物名称过长。")
    ((not (member (pl:get 'category s) '(0 1 2 3 4 5 6 7 8 9 10 11 12))) "形态分类无效。")
    (T nil)))
(defun pl:species-from-line (line / fields n s)
  (setq fields (pl:split-tab line))
  (if (member (length fields) '(7 8))
    (progn
      (setq n (pl:number-input (nth 2 fields)))
      (if (and n (= n (fix n)))
        (progn
          (setq s (list (cons 'id (nth 0 fields)) (cons 'name (nth 1 fields))
            (cons 'category (fix n)) (cons 'region (nth 3 fields))
            (cons 'source (nth 4 fields)) (cons 'note (nth 5 fields))
            (cons 'supply (nth 6 fields)) (cons 'tags (if (= (length fields) 8) (nth 7 fields) ""))))
          (if (not (pl:species-error s)) s nil))) ) nil))
(defun pl:species-line (s)
  (strcat (pl:get 'id s) "\t" (pl:get 'name s) "\t" (itoa (pl:get 'category s)) "\t"
    (pl:get 'region s) "\t" (pl:get 'source s) "\t" (pl:get 'note s) "\t"
    (if (pl:get 'supply s) (pl:get 'supply s) "待询价") "\t" (if (pl:get 'tags s) (pl:get 'tags s) "")))
(princ)

;;; Project plant lists are independent of placed-plant quantity schedules.
(defun pl:plant-list-rows (defs catalogue / rows seen p key name item species category region n)
  (setq rows nil seen nil n 0)
  (foreach p defs
    (setq name (pl:trim (pl:get 'name p)) key (pl:normal-name name))
    (if (not (member key seen))
      (progn
        (setq species nil)
        (foreach item catalogue
          (if (= (pl:get 'id item) (pl:get 'species_id p)) (setq species item)))
        (setq category (if species (nth (pl:get 'category species) (pl:category-names))
                         (pl:kind-name (pl:get 'kind p)))
              region (if species (pl:get 'region species) "")
              n (1+ n) seen (cons key seen))
        (setq rows (append rows (list (list (itoa n) name category region))))))) rows)
(defun pl:spec-list-rows (defs / rows p)
  (foreach p defs
    (setq p (pl:upgrade-plant p))
    (setq rows (append rows (list (list
      (pl:get 'spec_no p) (pl:get 'name p) (pl:kind-name (pl:get 'kind p))
      (pl:dimension-text 'dbh p) (pl:dimension-text 'caliper p)
      (pl:dimension-text 'height p) (pl:dimension-text 'crown p)
      (pl:get 'quantity_unit p)))))) rows)

;;; UI dimensions are centimetres; persisted height/crown remain metres for existing DWGs and MCP.
(defun pl:dimension-cm (key p / value)
  (setq value (pl:get key p))
  (if (member key '(height crown)) (* value 100.0) value))
(defun pl:diameter-placeholder (p)
  (<= (pl:diameter-value p) 0.0))
(defun pl:dimension-text (key p / value)
  (setq value (pl:dimension-cm key p))
  (if (and (member key '(dbh caliper)) (<= value 0.0))
    "——" (pl:num value)))
(defun pl:dimension-input (key text kind / value)
  (setq text (pl:trim text))
  (cond
    ((and (member key '(dbh caliper height crown)) (member text '("" "-" "—" "——" "--"))) 0.0)
    ((and (= text "") (member key '(dbh caliper height crown))) 0.0)
    ((setq value (pl:number-input text)) (if (member key '(height crown)) (/ value 100.0) value))
    (T nil)))
(defun pl:schedule-row (p quantity)
  (list (pl:get 'spec_no p) (pl:get 'name p)
    (pl:dimension-text 'dbh p) (pl:dimension-text 'caliper p)
    (pl:dimension-text 'height p) (pl:dimension-text 'crown p)
    (pl:quantity-text p quantity) (pl:get 'quantity_unit p)))
(defun pl:species-tags (s / result tag data)
  (setq result nil data (pl:get 'tags s))
  (cond ((member (pl:get 'category s) '(0 2)) (setq result '("常绿")))
        ((member (pl:get 'category s) '(1 3)) (setq result '("落叶"))))
  (foreach tag '("常绿" "落叶" "彩叶" "开花")
    (if (and data (vl-string-search tag data) (not (member tag result)))
      (setq result (append result (list tag))))) result)
(defun pl:species-caption (s / tags text tag)
  (setq tags (pl:species-tags s) text "")
  (if (assoc 'placement_kind s) (setq text (strcat "[" (pl:kind-name (pl:get 'placement_kind s)) "]")))
  (foreach tag tags (setq text (strcat text "[" tag "]")))
  (if (= text "") (setq text (strcat "[" (nth (pl:get 'category s) (pl:category-names)) "]")))
  (strcat text " " (pl:get 'name s)))
(defun pl:species-merge-selection (selected visible indexes / s result index chosen)
  ;; Keep selections hidden by the active filter, replace only the visible selection.
  (setq result nil chosen nil)
  (foreach index indexes
    (if (setq s (nth index visible)) (setq chosen (append chosen (list (pl:selection-id s))))))
  (foreach s selected
    (if (or (not (assoc (pl:selection-id s) (pl:species-index visible))) (member (pl:selection-id s) chosen))
      (setq result (append result (list s)))))
  (foreach index indexes
    (if (and (setq s (nth index visible)) (not (assoc (pl:selection-id s) (pl:species-index result))))
      (setq result (append result (list s))))) result)
(defun pl:selection-id (s)
  (if (assoc 'placement_kind s) (strcat (pl:get 'id s) ":ROLE:" (itoa (pl:get 'placement_kind s))) (pl:get 'id s)))
(defun pl:species-index (rows / result s)
  (foreach s rows (setq result (cons (cons (pl:selection-id s) s) result))) result)
(defun pl:indices-text (selected visible / index text s)
  (setq index 0 text "")
  (foreach s visible
    (if (assoc (pl:selection-id s) (pl:species-index selected))
      (setq text (strcat text (if (= text "") "" " ") (itoa index))))
    (setq index (1+ index))) text)

(defun pl:size-key (p)
  (if (/= (pl:get 'species_id p) "") (pl:get 'species_id p) (pl:normal-name (pl:get 'name p))))
(defun pl:default-size (kind)
  (cond ((= kind 0) '((crown . 3.0) (height . 4.0) (dbh . 12.0) (caliper . 0.0) (diameter_mode . 0)))
        ((= kind 3) '((crown . 1.0) (height . 1.0) (dbh . 0.0) (caliper . 0.0) (diameter_mode . 0)))
        ((= kind 1) '((crown . 0.6) (height . 0.6) (dbh . 0.0) (caliper . 0.0) (diameter_mode . 0)))
        (T '((crown . 0.0) (height . 0.0) (dbh . 0.0) (caliper . 0.0) (diameter_mode . 0)))))
(defun pl:seed-size (p defaults / saved pair)
  (setq saved (cdr (assoc (pl:size-key p) defaults)))
  (foreach pair (if saved saved (pl:default-size (pl:get 'kind p)))
    (setq p (pl:put (car pair) (cdr pair) p))) p)
(defun pl:project-filter (defs kind query / result row k)
  (setq query (strcase (pl:trim query)) result nil k 0)
  (repeat (length (pl:kind-names))
    (foreach row defs
      (if (and (= (pl:get 'kind row) k) (or (< kind 0) (= kind k))
        (or (= query "") (vl-string-search query (strcase (pl:get 'name row)))
                        (vl-string-search query (strcase (pl:get 'spec_no row)))))
        (setq result (append result (list row)))))
    (setq k (1+ k))) result)
(defun pl:unit-from-insunits (value) (cond ((= value 4) 0) ((= value 6) 1) ((= value 5) 2) (T -1)))
(defun pl:calibrated-units (measured actual_cm)
  (if (and (numberp measured) (numberp actual_cm) (> measured 0) (> actual_cm 0))
    (/ (* measured 100.0) actual_cm) nil))
