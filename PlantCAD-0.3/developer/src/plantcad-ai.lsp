;;; PlantCAD 0.3 - structured AI interface. Requires the matching in-process DLL.
;;; Only whitelisted data changes; no eval/read of AI-supplied Lisp code.
(setq pl:*ai-plans* nil)
(defun pl:ai-get (key pairs) (cadr (assoc key pairs)))
(defun pl:ai-o (fields) (cons "__object" fields))
(defun pl:ai-a (items) (cons "__array" items))
(defun pl:ai-error (message)
  (pl:ai-o (list (list "ok" nil) (list "error" message))))
(defun pl:ai-model-trees (/ e result)
  (foreach e (pl:all-trees)
    (if (not (equal 1 (cdr (assoc 67 (entget e))))) (setq result (cons e result))))
  (reverse result))
(defun pl:ai-targets (args / target scope handles candidates e h p name no result)
  (setq target (pl:ai-get "target" args) scope (pl:ai-get "scope" target))
  (if (not scope) (setq scope "selection"))
  (cond
    ((= scope "model") (setq candidates (pl:ai-model-trees)))
    ((member scope '("selection" "handles"))
      (setq handles (if (= scope "selection") (pl:ai-get "selected_handles" args) (pl:ai-get "handles" target)))
      (foreach h handles
        (setq e (handent h))
        (if (and e (pl:plant e)) (setq candidates (append candidates (list e)))
          (if (= scope "handles") (pl:fail (strcat "找不到植物句柄：" h))))))
    (T (pl:fail "目标范围无效。")))
  (setq name (pl:ai-get "name" target) no (pl:ai-get "spec_no" target))
  (foreach e candidates
    (setq p (pl:plant e))
    (if (and (or (not name) (= (pl:normal-name name) (pl:normal-name (pl:get 'name p))))
             (or (not no) (= (strcase no) (strcase (pl:get 'spec_no p))))
             (not (member e result)))
      (setq result (append result (list e))))) result)
(defun pl:ai-view (e p / pos units)
  (setq pos (trans (cdr (assoc 10 (entget e))) e 0) units (pl:data-get e "UNITS"))
  (pl:ai-o (list
    (list "handle" (cdr (assoc 5 (entget e))))
    (list "name" (pl:get 'name p)) (list "species_id" (pl:get 'species_id p))
    (list "spec_no" (pl:get 'spec_no p)) (list "kind" (pl:get 'kind p))
    (list "dbh_cm" (pl:get 'dbh p)) (list "caliper_cm" (pl:get 'caliper p))
    (list "height_m" (pl:get 'height p)) (list "crown_m" (pl:get 'crown p))
    (list "factor" (pl:get 'factor p))
    (list "style" (nth (pl:get 'style p) '("circle" "simple" "custom")))
    (list "diameter_mode" (if (= (pl:get 'diameter_mode p) 1) "caliper" "dbh"))
    (list "position" (pl:ai-a pos)) (list "units_per_m" (if units units 0))
    (list "locked" (not (pl:writable e))))))
(defun pl:ai-state (e / ed child attrs)
  (setq ed (entget e) attrs nil)
  (if (= (cdr (assoc 66 ed)) 1)
    (progn
      (setq child (entnext e))
      (while (and child (/= (cdr (assoc 0 (entget child))) "SEQEND"))
        (setq attrs (append attrs (list (entget child))) child (entnext child)))))
  (list ed (pl:data-get e "PLANT") (pl:data-get e "UNITS") attrs))
(defun pl:ai-context ()
  (list (pl:defs) (pl:db-get "SPEC_HISTORY" nil) (pl:catalog) (pl:db-get "AI_USED_IDS" nil) (pl:db-get "PLOT_OPTIONS" nil)))
(defun pl:ai-change-plant (p changes / pair field value mapped msg)
  (setq p (pl:upgrade-plant p))
  (foreach pair changes
    (setq field (car pair) value (cadr pair))
    (if (not (member field '("name" "species_id" "new_species_category" "dbh" "caliper" "height" "crown"
      "factor" "style" "diameter_mode" "dx_m" "dy_m"))) (pl:fail "修改包含不支持的字段。"))
    (cond
      ((member field '("dbh" "caliper" "height" "crown" "factor" "dx_m" "dy_m"))
        (if (not (numberp value)) (pl:fail "尺寸和位移必须是数字。"))
        (if (member field '("dbh" "caliper" "height" "crown" "factor"))
          (progn
            (setq mapped (cadr (assoc field '(("dbh" dbh) ("caliper" caliper) ("height" height) ("crown" crown) ("factor" factor)))))
            (setq p (pl:put mapped value p)))))
      ((= field "name") (setq p (pl:put 'name (pl:trim value) p)))
      ((= field "style")
        (if (not (member value '("circle" "simple"))) (pl:fail "只支持圆圈或简笔图例。"))
        (setq p (pl:put 'style (if (= value "simple") 1 0) p)))
      ((= field "diameter_mode")
        (if (not (member value '("dbh" "caliper"))) (pl:fail "径值类型无效。"))
        (setq p (pl:put 'diameter_mode (if (= value "caliper") 1 0) p)))))
  (if (setq msg (pl:insert-error p)) (pl:fail msg)) p)
(defun pl:ai-species (p old changes / wanted species row category)
  (if (or (assoc "species_id" changes)
          (and (assoc "name" changes) (/= (pl:normal-name (pl:get 'name p)) (pl:normal-name (pl:get 'name old)))))
    (progn
      (setq wanted (pl:ai-get "species_id" changes) species nil)
      (foreach row (pl:catalog)
        (if (if wanted (= wanted (pl:get 'id row))
              (= (pl:normal-name (pl:get 'name p)) (pl:normal-name (pl:get 'name row))))
          (if species (pl:fail "品种名称有多个匹配，请指定species_id。") (setq species row))))
      (if species
        (setq p (pl:put 'species_id (pl:get 'id species) p)
              p (pl:put 'name (pl:get 'name species) p)
              p (pl:put 'kind (pl:species-kind (pl:get 'category species)) p))
        (progn
          (if wanted (pl:fail "找不到指定的品种ID。"))
          (setq category (pl:ai-get "new_species_category" changes))
          (if (not (and (numberp category) (= category (fix category)) (>= category 0) (<= category 12)))
            (pl:fail "新名称不在品种库中。请先判读名称，新增时明确提供new_species_category。"))
          (setq p (pl:put 'species_id (strcat "AI_NEW_" (pl:get 'name p)) p)
                p (pl:put 'kind (pl:species-kind (fix category)) p)))))) p)
(defun pl:ai-read-plants (args / targets limit rows e)
  (setq targets (pl:ai-targets args) limit (pl:ai-get "limit" args))
  (if (not limit) (setq limit 200))
  (setq limit (fix (max 1 (min 500 limit))) rows nil)
  (foreach e targets
    (if (< (length rows) limit) (setq rows (append rows (list (pl:ai-view e (pl:plant e)))))))
  (pl:ai-o (list (list "ok" T) (list "count" (length targets))
    (list "returned" (length rows)) (list "plants" (pl:ai-a rows)))))
(defun pl:ai-read-catalogue (args / rows source limit s query)
  (setq query (pl:ai-get "query" args) limit (pl:ai-get "limit" args))
  (if (not query) (setq query ""))
  (if (not limit) (setq limit 100))
  (setq source (pl:species-filter (pl:catalog) -1 query "") rows nil limit (fix (max 1 (min 200 limit))))
  (foreach s source
    (if (< (length rows) limit)
      (setq rows (append rows (list (pl:ai-o (list
        (list "id" (pl:get 'id s)) (list "name" (pl:get 'name s))
        (list "category" (pl:get 'category s)) (list "region" (pl:get 'region s))
        (list "supply" (pl:get 'supply s)))))))))
  (pl:ai-o (list (list "ok" T) (list "count" (length source)) (list "species" (pl:ai-a rows)))))
(defun pl:ai-preview (args / targets changes id defs entries output e old p row match index msg plan)
  (setq targets (pl:ai-targets args) changes (pl:ai-get "changes" args) id (pl:ai-get "plan_id" args))
  (if (or (not id) (= id "") (not changes)) (pl:fail "预览参数不完整。"))
  (if (not targets) (pl:fail "没有匹配的植物；请在CAD中选择植物，或明确提供句柄/模型范围。"))
  (if (> (length targets) 500) (pl:fail "一次最多调整500个植物对象。"))
  (setq defs (pl:used-specs) entries nil output nil index 0)
  (foreach e targets
    (if (not (pl:writable e)) (pl:fail "目标中有锁定对象，请先处理锁定图层。"))
    (if (not (and (pl:data-get e "UNITS") (> (pl:data-get e "UNITS") 0))) (pl:fail "植物插入单位记录缺失。"))
    (setq old (pl:plant e) p (pl:ai-change-plant old changes) p (pl:ai-species p old changes))
    (if (not (pl:layer-open (pl:tree-layer p))) (pl:fail "目标图例图层已锁定。"))
    (if (and (= (pl:get 'style p) 2) (setq msg (pl:custom-error (pl:get 'block p)))) (pl:fail msg))
    (if (or (not (equal (pl:physical-key old) (pl:physical-key p)))
            (/= (pl:get 'species_id old) (pl:get 'species_id p)))
      (progn
        (setq match nil)
        (foreach row defs (if (and (equal (pl:physical-key row) (pl:physical-key p))
            (= (pl:get 'species_id row) (pl:get 'species_id p))) (setq match row)))
        (if match
          (setq p (pl:put 'id (pl:get 'id match) p) p (pl:put 'spec_no (pl:get 'spec_no match) p))
          (progn
            (setq index (1+ index)
              p (pl:put 'id (strcat "AI_SPEC_" id "_" (itoa index)) p)
              p (pl:put 'spec_no (pl:next-spec-number defs) p)
              defs (append defs (list p)))))))
    (setq entries (append entries (list (list e (pl:ai-state e) p))))
    (setq output (append output (list (pl:ai-o (list
      (list "before" (pl:ai-view e old)) (list "after" (pl:ai-view e p))
      (list "dx_m" (if (pl:ai-get "dx_m" changes) (pl:ai-get "dx_m" changes) 0))
      (list "dy_m" (if (pl:ai-get "dy_m" changes) (pl:ai-get "dy_m" changes) 0))))))))
  (setq plan (list id (pl:ai-context) entries changes (getvar "DATE"))
        pl:*ai-plans* (cons plan pl:*ai-plans*))
  (if (> (length pl:*ai-plans*) 20) (setq pl:*ai-plans* (reverse (cdr (reverse pl:*ai-plans*)))))
  (pl:ai-o (list (list "ok" T) (list "plan_id" id)
    (list "count" (length entries)) (list "changes" (pl:ai-a output)))))
(defun pl:ai-track-used (/ ids e id)
  (setq ids (pl:db-get "AI_USED_IDS" nil))
  (foreach e (pl:ai-model-trees)
    (setq id (pl:get 'id (pl:plant e)))
    (if (not (member id ids)) (setq ids (append ids (list id)))))
  (pl:db-put "AI_USED_IDS" ids))
(defun pl:ai-visible-defs (/ current former e p id result)
  (setq current nil former (pl:db-get "AI_USED_IDS" nil))
  (foreach e (pl:ai-model-trees) (setq current (cons (pl:get 'id (pl:plant e)) current)))
  (foreach e (append (pl:all-areas) (pl:all-project-sources))
    (if (and (not (equal 1 (cdr (assoc 67 (entget e))))) (setq p (pl:annotation-plant e)))
      (setq current (cons (pl:get 'id p) current))))
  (foreach p (pl:defs)
    (setq id (pl:get 'id p))
    (if (or (not (member id former)) (member id current)) (setq result (append result (list p))))) result)
(defun pl:ai-table-rows (e / layer scope targets h tree)
  (setq layer (cdr (assoc 8 (entget e))) scope (pl:data-get e "TABLE_SCOPE"))
  (cond
    ((= layer "PL_表格_植物名录") (pl:plant-list-rows (pl:ai-visible-defs) (pl:catalog)))
    ((= layer "PL_表格_植物规格") (pl:spec-list-rows (pl:ai-visible-defs)))
    ((and (= layer "PL_表格_苗木") scope)
      (if (= (pl:get 'scope scope) "model") (setq targets (pl:statistics-model))
        (foreach h (pl:get 'handles scope)
          (if (and (setq tree (handent h)) (pl:quantity-data tree)) (setq targets (append targets (list tree))))))
      (pl:ai-quantity-rows (pl:count-rows targets)))
    (T nil)))
(defun pl:ai-quantity-rows (counts / rows row)
  (foreach row counts (setq rows (append rows (list (pl:schedule-row (cadr row) (caddr row)))))) rows)
(defun pl:ai-update-table (obj rows / suppressed result)
  ;; AutoCAD 2014 otherwise regenerates the entire table for every SetText call.
  (setq suppressed (vla-get-RegenerateTableSuppressed obj))
  (vla-put-RegenerateTableSuppressed obj :vlax-true)
  (setq result (vl-catch-all-apply 'pl:ai-update-table-cells (list obj rows)))
  (vla-put-RegenerateTableSuppressed obj suppressed)
  (if (vl-catch-all-error-p result) (pl:rethrow result) result))
(defun pl:ai-update-table-cells (obj rows / needed existing i col row value layer headers changed)
  ;; Update units with row values when refreshing a table created by an earlier build.
  (setq layer (vla-get-Layer obj)
    headers (cond
      ((= layer "PL_表格_苗木") '("规格编号" "植物名称" "胸径 cm" "地径 cm" "高度 cm" "冠幅 cm" "数量" "单位"))
      ((= layer "PL_表格_植物规格") '("规格编号" "植物名称" "类别" "胸径 cm" "地径 cm" "高度 cm" "冠幅 cm" "单位"))
      (T nil)))
  (setq col 0)
  (foreach value headers
    (if (not (equal (vla-GetText obj 1 col) value)) (progn (vla-SetText obj 1 col value) (setq changed T)))
    (setq col (1+ col)))
  (setq needed (+ 2 (length rows)) existing (vla-get-Rows obj))
  (cond ((> existing needed) (vla-DeleteRows obj needed (- existing needed)) (setq changed T))
    ((< existing needed) (vla-InsertRows obj existing (vla-GetRowHeight obj (1- existing)) (- needed existing)) (setq changed T)))
  (setq i 2)
  (foreach row rows
    (setq col 0)
    (foreach value row
      (if (not (equal (vla-GetText obj i col) value)) (progn (vla-SetText obj i col value) (setq changed T)))
      (setq col (1+ col)))
    (setq i (1+ i)))
  (if changed (vla-Update obj)) T)
(defun pl:ai-refresh-tables (/ e layer rows obj columns result n skipped)
  (setq n 0 skipped 0)
  (foreach e (pl:ss-list (ssget "_X" '((0 . "ACAD_TABLE") (-3 ("PLANTCAD01")))))
    (setq layer (cdr (assoc 8 (entget e))))
    (if (and (= (pl:role e) "TABLE")
      (member layer '("PL_表格_植物名录" "PL_表格_植物规格" "PL_表格_苗木")))
      (progn
        (if (pl:data-get e "TABLE_KIND")
          (if (vl-catch-all-error-p (vl-catch-all-apply 'pl:output-table-refresh (list e))) (setq skipped (1+ skipped)) (setq n (1+ n)))
        (progn
        (setq obj (vlax-ename->vla-object e) columns (if (= layer "PL_表格_植物名录") 4 8))
        (if (and (pl:writable e) (= (vla-get-Columns obj) columns) (>= (vla-get-Rows obj) 2)
          (or (/= layer "PL_表格_苗木") (pl:data-get e "TABLE_SCOPE")))
          (progn
            (setq rows (pl:ai-table-rows e)
              result (vl-catch-all-apply 'pl:ai-update-table (list obj rows)))
            (if (vl-catch-all-error-p result) (setq skipped (1+ skipped)) (setq n (1+ n))))
          (setq skipped (1+ skipped))))))))
  (list n skipped))
(defun pl:ai-commit-species (p changes mapping / sid row s found category)
  (setq sid (pl:get 'species_id p))
  (if (= (substr sid 1 7) "AI_NEW_")
    (progn
      (setq found (assoc sid mapping))
      (if found (setq p (pl:put 'species_id (cadr found) p))
        (progn
          (setq category (fix (pl:ai-get "new_species_category" changes)))
          (setq s (list (cons 'id (pl:new-id)) (cons 'name (pl:get 'name p))
            (cons 'category category) (cons 'region "") (cons 'source "设计师经AI桌面新增")
            (cons 'note "") (cons 'supply "待询价")))
          (pl:db-put "CATALOG" (append (pl:catalog) (list s)))
          (setq mapping (append mapping (list (list sid (pl:get 'id s))))
                p (pl:put 'species_id (pl:get 'id s) p))))))
  (list p mapping))
(defun pl:ai-apply (args / plan id entries changes entry e p result defs mapping specmap original dx dy units obj output tables retained candidate)
  (setq id (pl:ai-get "plan_id" args) plan (assoc id pl:*ai-plans*))
  (if (not plan) (pl:fail "预览计划不存在，请重新预览。"))
  (if (> (- (getvar "DATE") (nth 4 plan)) 0.00695) (pl:fail "预览已过期，请重新预览。"))
  (if (not (equal (cadr plan) (pl:ai-context))) (pl:fail "项目植物数据已变化，请重新预览。"))
  (setq entries (nth 2 plan) changes (nth 3 plan))
  (foreach entry entries
    (setq e (car entry) p (nth 2 entry))
    (if (or (not (entget e)) (not (pl:writable e)) (not (pl:layer-open (pl:tree-layer p)))
            (not (equal (cadr entry) (pl:ai-state e)))) (pl:fail "植物已变化或图层已锁定，请重新预览。")))
  (pl:ai-track-used)
  (setq mapping nil specmap nil output nil)
  (foreach entry entries
    (setq e (car entry) p (nth 2 entry) result (pl:ai-commit-species p changes mapping)
      p (car result) mapping (cadr result) original (pl:get 'id p))
    (if (= (substr original 1 8) "AI_SPEC_")
      (if (setq result (assoc original specmap))
        (setq p (pl:put 'id (cadr result) p))
        (progn
          (setq p (pl:put 'id (pl:new-id) p))
          (pl:save-def p)
          (setq specmap (append specmap (list (list original (pl:get 'id p))))))))
    (if (not (pl:apply-plant e p)) (pl:fail "植物更新失败。"))
    (setq dx (pl:ai-get "dx_m" changes) dy (pl:ai-get "dy_m" changes) units (pl:data-get e "UNITS"))
    (if (or dx dy)
      (progn
        (setq obj (vlax-ename->vla-object e))
        (vla-Move obj (vlax-3d-point '(0.0 0.0 0.0))
          (vlax-3d-point (list (* (if dx dx 0) units) (* (if dy dy 0) units) 0.0)))
        (pl:refresh-symbol e)))
    (setq output (append output (list (pl:ai-view e p)))))
  (pl:ai-track-used) (pl:sync-labels) (setq tables (pl:ai-refresh-tables))
  (setq retained nil)
  (foreach candidate pl:*ai-plans*
    (if (/= id (car candidate)) (setq retained (append retained (list candidate)))))
  (setq pl:*ai-plans* retained)
  (pl:ai-o (list (list "ok" T) (list "count" (length entries))
    (list "plants" (pl:ai-a output)) (list "tables_updated" (car tables))
    (list "tables_skipped" (cadr tables))
    (list "note" "已更新植物、文字和受管理表格；跳过锁定、结构不匹配、更新失败或缺少范围记录的旧表，请核对跳过数量。可在CAD用U撤销，未自动保存图纸。"))))
(defun pl:ai-plot (args / opts value)
  (setq opts (pl:plot-options))
  (foreach value args
    (if (member (car value) '("scale" "paper_height"))
      (progn
        (if (not (and (numberp (cadr value)) (> (cadr value) 0))) (pl:fail "比例和字高必须大于0。"))
        (setq opts (pl:put (if (= (car value) "scale") 'scale 'paper_height) (cadr value) opts)))))
  (pl:db-put "PLOT_OPTIONS" opts) (pl:sync-labels)
  (pl:ai-o (list (list "ok" T) (list "scale" (pl:get 'scale opts))
    (list "paper_height_mm" (pl:get 'paper_height opts)))))
(defun pl:ai-work (action args)
  (cond ((= action "panel_state") (pl:ui-state))
    ((= action "get_plants") (pl:ai-read-plants args))
    ((= action "catalogue") (pl:ai-read-catalogue args))
    ((= action "preview_adjust") (pl:ai-preview args))
    ((= action "apply_adjust") (pl:ai-apply args))
    ((= action "plot_settings") (pl:ai-plot args))
    (T (pl:ai-error "不支持此操作。"))))
(defun pl:ai-dispatch (action args / result doc mutate)
  (setq pl:*failure* nil mutate (member action '("apply_adjust" "plot_settings")))
  (if mutate (progn (setq doc (pl:doc)) (vla-StartUndoMark doc)))
  (setq result (vl-catch-all-apply 'pl:ai-work (list action args)))
  (if mutate (vl-catch-all-apply 'vla-EndUndoMark (list doc)))
  (if (vl-catch-all-error-p result)
    (pl:ai-o (list (list "ok" nil)
      (list "error" (if pl:*failure* pl:*failure* (vl-catch-all-error-message result)))
      (list "partial_changes_possible" (if mutate T nil))
      (list "note" "失败后先读取图纸核对；如已有改动，可用CAD的U撤销，不要盲目重试。"))) result))
(vl-acad-defun 'pl:ai-dispatch)
(princ "\nCountingTrees（数树） AI数据接口已加载。")
(princ)
