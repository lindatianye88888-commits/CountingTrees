;;; Optional pure-rule check in the REAL CAD Lisp interpreter.
;;; Load after plantcad.lsp, then run PLCHECK. Does not modify drawing entities.
(defun pl:check-equal (actual expected label)
  (if (equal actual expected 0.000001)
    (progn (setq pl:*check-pass* (1+ pl:*check-pass*)) (princ (strcat "\n通过：" label)))
    (progn (setq pl:*check-fail* (1+ pl:*check-fail*))
      (princ (strcat "\n失败：" label)) (prin1 actual))))

(defun c:PLCHECK (/ p q opts rows)
  (setq pl:*check-pass* 0 pl:*check-fail* 0)
  (setq p (pl:empty-plant "CHECK"))
  (setq p (pl:put 'name "香樟" p) p (pl:put 'dbh 12.0 p)
        p (pl:put 'height 4.0 p) p (pl:put 'crown 3.0 p))
  (setq opts '((mode . 1) (prefix . 0) (units . 0)))
  (pl:check-equal (pl:label-text p opts) "香樟\\P12" "名称下行胸径数字")
  (pl:check-equal (pl:label-text (pl:put 'dbh 0.0 p) opts) "香樟" "缺少胸径不显示横杠")
  (pl:check-equal (pl:diameter p 1000.0) 3000.0 "毫米换算")
  (pl:check-equal (pl:diameter p 1.0) 3.0 "米换算")
  (setq q (pl:put 'factor 0.8 p))
  (pl:check-equal (pl:diameter q 1000.0) 2400.0 "显示缩放")
  (pl:check-equal (pl:get 'crown q) 3.0 "实际冠幅保留")
  (pl:check-equal (pl:get 'dbh q) 12.0 "胸径保留")
  (setq rows (pl:add-count p nil))
  (setq rows (pl:add-count (pl:put 'style 1 q) rows))
  (pl:check-equal (length rows) 1 "不同图例合并")
  (pl:check-equal (caddr (car rows)) 2 "计数2株")
  (setq rows (pl:add-count (pl:put 'dbh 15.0 p) rows))
  (pl:check-equal (length rows) 2 "不同胸径分行")
  (pl:check-equal (pl:number-input "12cm") nil "拒绝单位文字")
  (pl:check-equal (pl:number-input "-12") nil "拒绝负数")
  (setq q (pl:put 'caliper 8.0 p) q (pl:put 'diameter_mode 1 q))
  (pl:check-equal (pl:label-text q opts) "香樟\\P8" "下行可选地径")
  (pl:check-equal (pl:label-text (pl:put 'caliper 0.0 q) opts) "香樟" "缺少地径不借用胸径")
  (pl:check-equal (pl:paper-height 2.5 100.0 1000.0) 250.0 "1:100纸面字高换算")
  (pl:check-equal (pl:diameter (pl:put 'crown 5.0 p) 1000.0) 5000.0 "5米冠幅")
  (pl:check-equal (pl:next-spec-number nil) "P001" "起始规格编号")
  (princ (strcat "\n真实CAD解释器规则检查：通过 " (itoa pl:*check-pass*)
    "，失败 " (itoa pl:*check-fail*) "。界面、存储和几何仍需实测。"))
  (princ))

(princ "\n已加载规则检查命令 PLCHECK。")
(princ)
