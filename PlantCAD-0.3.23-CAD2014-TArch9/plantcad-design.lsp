;;; PlantCAD 0.3 - catalogue, specifications and embedded symbol text.
;;; No network requests and no evaluation of catalogue contents at runtime.
(defun pl:read-catalog (path / file line rows seen s invalid header)
  (setq file (open path "r") rows nil seen nil invalid nil)
  (if file
    (progn
      (setq header (read-line file))
      (if (not (member header '("id\tname\tcategory\tregion\tsource\tnote\tsupply" "id\tname\tcategory\tregion\tsource\tnote\tsupply\ttags"))) (setq invalid T))
      (while (setq line (read-line file))
        (if (/= (pl:trim line) "")
          (progn (setq s (pl:species-from-line line))
            (if (or (not s) (member (if s (strcase (pl:get 'id s))) seen))
              (setq invalid T)
              (setq rows (append rows (list s)) seen (cons (strcase (pl:get 'id s)) seen))))))
      (close file)
      (if (or invalid (not rows)) nil rows)) nil))
(defun pl:catalog (/ rows)
  (setq rows (pl:db-get "CATALOG" nil))
  (if (not rows) (setq rows (pl:read-catalog (strcat pl:*dir* "/plantcatalog.tsv"))))
  rows)
(defun pl:write-catalog (file rows / s)
  (write-line "id\tname\tcategory\tregion\tsource\tnote\tsupply\ttags" file)
  (foreach s rows (write-line (pl:species-line s) file)))
(defun pl:catalog-export (/ path file result)
  (if (setq path (getfiled "导出共享品种表（GBK/ANSI制表符文本）" "植物品种表.tsv" "tsv" 1))
    (progn (setq file (open path "w"))
      (if (not file) (pl:fail "无法写入品种表。"))
      (setq result (vl-catch-all-apply 'pl:write-catalog (list file (pl:catalog))))
      (close file)
      (if (vl-catch-all-error-p result) (pl:fail (vl-catch-all-error-message result))
        (princ (strcat "\n已导出品种表：" path))))))
(defun pl:catalog-import (/ path rows current s old row)
  (if (setq path (getfiled "导入共享品种表（须为GBK/ANSI，按ID合并）" "" "tsv" 0))
    (if (setq rows (pl:read-catalog path))
      (progn
        (setq current (pl:catalog))
        (foreach s rows
          (setq old nil)
          (foreach row current (if (= (strcase (pl:get 'id s)) (strcase (pl:get 'id row))) (setq old row)))
          (setq current (if old (subst s old current) (append current (list s)))))
        (pl:db-put "CATALOG" current)
        (princ (strcat "\n已合并 " (itoa (length rows)) " 个品种；项目规格保持原值。")))
      (alert "品种表无效：请检查GBK编码、表头、7列旧表或8列带标签字段、形态编号0-12及重复ID。未导入任何记录。"))))
(defun pl:catalog-selected-view (/ s)
  (start_list "chosen_species")
  (foreach s pl:*catalog-picked* (add_list (pl:species-caption s)))
  (end_list)
  (set_tile "chosen_count" (strcat "已选植物：" (itoa (length pl:*catalog-picked*)) " 项"))
  (setq pl:*picked-index* 0)
  (if pl:*catalog-picked* (set_tile "chosen_species" "0"))
  (mode_tile "remove_chosen" (if pl:*catalog-picked* 0 1))
  (mode_tile "clear_chosen" (if pl:*catalog-picked* 0 1))
  (mode_tile "accept" (if pl:*catalog-picked* 0 1)))
(defun pl:catalog-filter (/ category s)
  (setq category (1- (atoi (get_tile "category"))))
  (setq pl:*catalog-visible* (pl:species-filter pl:*catalog-rows* category
    (get_tile "query") (get_tile "region")))
  (start_list "species")
  (foreach s pl:*catalog-visible*
    (add_list (strcat (pl:species-caption s) "  " (pl:get 'region s) " | " (pl:get 'supply s))))
  (end_list)
  (setq pl:*catalog-selection* (pl:indices-text pl:*catalog-picked* pl:*catalog-visible*))
  (set_tile "species" pl:*catalog-selection*)
  (set_tile "detail" (strcat "当前筛选 " (itoa (length pl:*catalog-visible*)) " 项；切换筛选保留右侧已选。"))
  (pl:catalog-selected-view))
(defun pl:catalog-select (value / indexes s)
  (setq pl:*catalog-selection* value indexes (read (strcat "(" value ")"))
        pl:*catalog-picked* (pl:species-merge-selection pl:*catalog-picked* pl:*catalog-visible* indexes))
  (if indexes
    (progn (setq s (nth (car indexes) pl:*catalog-visible*))
      (set_tile "detail" (strcat "备注：" (pl:get 'note s)))))
  (pl:catalog-selected-view))
(defun pl:catalog-remove-picked (/ n result s)
  (setq n 0 result nil)
  (foreach s pl:*catalog-picked*
    (if (/= n pl:*picked-index*) (setq result (append result (list s))))
    (setq n (1+ n)))
  (setq pl:*catalog-picked* result) (pl:catalog-filter))
(defun pl:catalog-clear-picked () (setq pl:*catalog-picked* nil) (pl:catalog-filter))
(defun pl:catalog-accept ()
  (setq pl:*catalog-result* pl:*catalog-picked*)
  (if pl:*catalog-result* (done_dialog 1) (set_tile "error" "请先在左侧选择植物，右侧会列出已选项目。")))
(defun pl:species-category-change (value / category)
  (setq category (atoi value))
  (set_tile "evergreen" (if (member category '(0 2)) "1" "0"))
  (set_tile "deciduous" (if (member category '(1 3)) "1" "0")))
(defun pl:accept-species (/ s key msg tags pair)
  (setq s pl:*species-edit* tags "")
  (foreach key '(name region source note supply)
    (setq s (pl:put key (pl:trim (get_tile (strcase (vl-symbol-name key) T))) s)))
  (foreach pair '(("evergreen" "常绿") ("deciduous" "落叶") ("color_leaf" "彩叶") ("flowering" "开花"))
    (if (= (get_tile (car pair)) "1") (setq tags (strcat tags (if (= tags "") "" "|") (cadr pair)))))
  (setq s (pl:put 'tags tags (pl:put 'category (atoi (get_tile "category")) s)) msg (pl:species-error s))
  (if (and (= (get_tile "evergreen") "1") (= (get_tile "deciduous") "1")) (setq msg "常绿与落叶不能同时勾选。"))
  (if msg (set_tile "error" msg)
    (progn (setq pl:*species-result* s) (done_dialog 1))))
(defun pl:species-dialog (s / id status key pair tags)
  (setq id (pl:dialog "pl_species") pl:*species-edit* s pl:*species-result* nil)
  (if id
    (progn
      (set_tile "identity" (strcat "品种ID：" (pl:get 'id s) "（项目规格与品种关联，已有规格需另行修改）"))
      (pl:popup "category" (pl:category-names))
      (set_tile "category" (itoa (pl:get 'category s)))
      (foreach key '(name region source note supply)
        (set_tile (strcase (vl-symbol-name key) T) (pl:get key s)))
      (setq tags (pl:species-tags s))
      (foreach pair '(("evergreen" "常绿") ("deciduous" "落叶") ("color_leaf" "彩叶") ("flowering" "开花"))
        (set_tile (car pair) (if (member (cadr pair) tags) "1" "0")))
      (action_tile "category" "(pl:species-category-change $value)")
      (action_tile "accept" "(pl:accept-species)")
      (action_tile "cancel" "(done_dialog 0)")
      (setq status (start_dialog)) (unload_dialog id)
      (if (= status 1) pl:*species-result* nil))))
(defun pl:catalog-pick (/ dlg status quit selection s old rows)
  (setq quit nil pl:*catalog-result* nil pl:*catalog-picked* (pl:db-get "CATALOG_PICKED" nil))
  (while (not quit)
    (setq pl:*catalog-rows* (pl:catalog) dlg (pl:dialog "pl_catalog"))
    (if (not dlg) (setq quit T)
      (progn
        (pl:popup "category" (cons "全部形态" (pl:category-names)))
        (set_tile "category" "0") (set_tile "query" "") (set_tile "region" "")
        (pl:catalog-filter)
        (action_tile "species" "(pl:catalog-select $value)")
        (action_tile "chosen_species" "(setq pl:*picked-index* (atoi $value))")
        (action_tile "remove_chosen" "(pl:catalog-remove-picked)")
        (action_tile "clear_chosen" "(pl:catalog-clear-picked)")
        (action_tile "filter" "(pl:catalog-filter)")
        (action_tile "category" "(pl:catalog-filter)")
        (action_tile "accept" "(pl:catalog-accept)")
        (action_tile "cancel" "(done_dialog 0)")
        (action_tile "add" "(done_dialog 2)")
        (action_tile "edit" "(done_dialog 3)")
        (action_tile "export" "(done_dialog 4)")
        (action_tile "import" "(done_dialog 5)")
        (setq status (start_dialog)
              selection (read (strcat "(" pl:*catalog-selection* ")")))
        (unload_dialog dlg)
        (cond
          ((member status '(0 1)) (setq quit T))
          ((= status 2)
            (setq s (pl:species-dialog (list (cons 'id (pl:new-id)) (cons 'name "")
              (cons 'category 0) (cons 'region "") (cons 'source "设计师增补")
              (cons 'note "") (cons 'supply "待询价"))))
            (if s (pl:db-put "CATALOG" (append (pl:catalog) (list s)))))
          ((= status 3)
            (if (= (length selection) 1)
              (progn (setq old (nth (car selection) pl:*catalog-visible*) s (pl:species-dialog old))
                (if s (progn (pl:db-put "CATALOG" (subst s old (pl:catalog)))
                  (setq pl:*catalog-picked* (subst s old pl:*catalog-picked*)))))
              (alert "修改品种时请选择一项。")))
          ((= status 4) (pl:catalog-export))
          ((= status 5) (pl:catalog-import))))))
  (pl:db-put "CATALOG_PICKED" pl:*catalog-picked*)
  pl:*catalog-result*)
(defun pl:new-spec (species / p)
  (setq p (pl:empty-plant (pl:new-id)))
  (setq p (pl:put 'spec_no (pl:next-spec-number (pl:used-specs)) p))
  (if species
    (setq p (pl:put 'name (pl:get 'name species) p)
          p (pl:put 'species_id (pl:get 'id species) p)
          p (pl:put 'kind (if (assoc 'placement_kind species) (pl:get 'placement_kind species) (pl:species-kind (pl:get 'category species))) p)
          p (pl:put 'quantity_unit (if (member (pl:get 'category species) '(5 6)) "丛" "株") p)))
  (pl:seed-size p (pl:project-size-defaults)))
(defun pl:add-from-catalog (/ species p added)
  (setq added 0)
  (foreach species (pl:catalog-pick)
    (setq p (pl:edit-dialog (pl:new-spec species)))
    (if p (progn (pl:save-def p) (pl:db-put "CURRENT" (pl:get 'id p)) (setq added (1+ added)))))
  (princ (strcat "\n已建立 " (itoa added) " 个规格。可复制同一品种继续建立不同规格。")) added)
(defun pl:project-row-action (value reason)
  (setq pl:*index* (atoi value))
  (if (= reason 4) (done_dialog 3)))
(defun pl:legacy-project-dialog (index / dlg status)
  (setq dlg (pl:dialog "pl_library") status 0)
  (if dlg
    (progn
        (pl:popup "project_kind" (cons "全部分类" (pl:kind-names)))
        (set_tile "project_kind" "0") (set_tile "project_query" "")
        (pl:project-filter-dialog)
        (setq pl:*index* (if (< index (length pl:*project-visible*)) index 0))
        (if pl:*project-visible* (set_tile "plants" (itoa pl:*index*)))
        (action_tile "project_filter" "(pl:project-filter-dialog)")
        (action_tile "project_kind" "(pl:project-filter-dialog)")
        (action_tile "project_query" "(pl:project-filter-dialog)")
        (action_tile "plants" "(pl:project-row-action $value $reason)")
        (action_tile "add" "(done_dialog 2)")
        (action_tile "edit" "(done_dialog 3)")
        (action_tile "update" "(done_dialog 4)")
        (action_tile "manual" "(done_dialog 5)")
        (action_tile "clone" "(done_dialog 6)")
        (action_tile "accept" "(done_dialog 1)")
        (action_tile "place" "(done_dialog 7)")
        (action_tile "cancel" "(done_dialog 0)")
        (setq status (start_dialog)) (unload_dialog dlg))) status)
(defun pl:project-dialog (index / result)
  (if (and (boundp 'pl:*native-ui*) pl:*native-ui*)
    (progn
      (setq pl:*project-visible* (pl:defs)
        result (pl:native-project-dialog (mapcar 'pl:project-list-row pl:*project-visible*) (pl:kind-names) index))
      (if (not (and (listp result) (numberp (car result)) (numberp (cadr result))))
        (pl:fail (if (= (type result) 'STR) result "项目窗口返回格式无效。")))
      (setq pl:*index* (max 0 (cadr result))) (car result))
    (pl:legacy-project-dialog index)))
(defun pl:design-library (/ status index p quit)
  (setq index 0 quit nil)
  (while (not quit)
    (setq status (pl:project-dialog index) index pl:*index* p (nth index pl:*project-visible*))
        (cond
          ((= status 0) (setq quit T))
          ((= status 2) (pl:add-from-catalog) (setq index (max 0 (1- (length (pl:defs))))))
          ((= status 5) (setq p (pl:edit-dialog (pl:new-spec nil)))
            (if p (progn (pl:save-def p) (setq index (max 0 (1- (length (pl:defs))))))))
          ((and (= status 6) p)
            (setq p (pl:put 'id (pl:new-id) p)
                  p (pl:put 'spec_no (pl:next-spec-number (pl:used-specs)) p)
                  p (pl:edit-dialog p))
            (if p (progn (pl:save-def p) (setq index (max 0 (1- (length (pl:defs))))))))
          ((and (= status 3) p) (setq p (pl:edit-project-dialog p)) (if p (pl:save-project-spec p)))
          ((and (= status 4) p) (pl:update-from-def p))
          ((and (= status 7) p) (pl:db-put "CURRENT" (pl:get 'id p)) (setq quit T) (pl:placement-menu-work))
          ((and (= status 1) p) (pl:db-put "CURRENT" (pl:get 'id p))
            (princ (strcat "\n当前规格：" (pl:get 'spec_no p) " " (pl:get 'name p))) (setq quit T)))))
(defun pl:design-start () (if (> (pl:add-from-catalog) 0) (pl:library-work)))
(defun pl:migrate-defs (/ defs result p e raw)
  (setq defs (pl:db-get "PLANTS" nil) result nil)
  (foreach p defs
    (setq p (pl:upgrade-plant p))
    (if (= (pl:get 'spec_no p) "")
      (setq p (pl:put 'spec_no (pl:next-spec-number
        (append result defs (pl:db-get "SPEC_HISTORY" nil))) p)))
    (setq result (append result (list p))))
  (if result (pl:db-put "PLANTS" result))
  (foreach p result (pl:remember-spec p))
  ;; Legacy snapshots may have a crown changed from their old library definition.
  ;; Migrate metadata only, preserving entity handles, positions, labels and art.
  (foreach e (pl:all-trees)
    (setq raw (pl:data-get e "PLANT"))
    (if (and raw (not (assoc 'spec_no raw)) (pl:writable e))
      (progn
        (setq p (pl:instance-variant (pl:upgrade-plant raw)))
        (pl:data-put e "PLANT" p)))))

(defun pl:accept-settings (/ scale height)
  (setq scale (pl:number-input (get_tile "plot_scale"))
        height (pl:number-input (get_tile "paper_height")))
  (if (and scale height (> scale 0) (> height 0)
    (or (/= (get_tile "unit") "3") (pl:db-get "UNITS_PER_M" nil)))
    (progn
      (setq pl:*settings-result* (list (cons 'scale scale) (cons 'paper_height (* height 10.0))
        (cons 'show_number (atoi (get_tile "show_number")))
        (cons 'unit (atoi (get_tile "unit"))))) (done_dialog 1))
    (set_tile "error" "比例和字高须大于0；自定义单位请先使用“按已知长度校准”。")))
(defun pl:design-settings (/ dlg status opts u)
  (setq dlg (pl:dialog "pl_settings") u (pl:unit-index)
        opts (pl:db-get "PLOT_OPTIONS" '((scale . 100.0) (paper_height . 2.5) (show_number . 0))))
  (if dlg
    (progn
      (pl:popup "unit" '("毫米 mm" "米 m" "厘米 cm" "自定义（按已知长度校准）"))
      (set_tile "unit_hint" (strcat "CAD声明单位："
        (if (>= (pl:unit-from-insunits (getvar "INSUNITS")) 0)
          (nth (pl:unit-from-insunits (getvar "INSUNITS")) '("毫米" "米" "厘米")) "未设置或其他单位")
        "；请核对实际长度。"))
      (if (< u 0) (setq u (pl:unit-from-insunits (getvar "INSUNITS"))))
      (set_tile "unit" (itoa (if (< u 0) 0 u)))
      (set_tile "plot_scale" (pl:num (pl:get 'scale opts)))
      (set_tile "paper_height" (pl:num (/ (pl:get 'paper_height opts) 10.0)))
      (set_tile "show_number" (itoa (pl:get 'show_number opts)))
      (action_tile "accept" "(pl:accept-settings)") (action_tile "cancel" "(done_dialog 0)")
      (setq status (start_dialog)) (unload_dialog dlg)
      (if (= status 1)
        (progn (pl:db-put "UNIT" (pl:get 'unit pl:*settings-result*))
          (pl:db-put "PLOT_OPTIONS" pl:*settings-result*)
          (pl:refresh-all-symbols))))))
(defun pl:symbol-attdefs (/ pair)
  (foreach pair '(("PL_NAME" "植物名称") ("PL_DIAMETER" "胸径或地径") ("PL_SPEC" "规格编号"))
    (if (not (entmake (list '(0 . "ATTDEF") '(8 . "0") '(62 . 7) '(10 0.0 0.0 0.0)
      '(40 . 0.1) '(1 . "") (cons 3 (cadr pair)) (cons 2 (car pair))
      '(70 . 0) '(72 . 1) '(74 . 2) '(11 0.0 0.0 0.0) (cons 7 (getvar "TEXTSTYLE")))))
      (pl:fail "无法创建图例文字定义。"))))
(defun pl:custom-wrapper (p / source name)
  ;; Keep the editable original art as a nested reference, and attach our text outside it.
  (setq source (pl:get 'block p))
  (if (pl:custom-error source) (pl:fail (pl:custom-error source)))
  (setq name (strcat "PL02_WRAP_" (cdr (assoc 5 (entget (tblobjname "BLOCK" source))))))
  (if (not (tblsearch "BLOCK" name))
    (progn
      (if (not (entmake (list '(0 . "BLOCK") (cons 2 name) '(70 . 2) '(8 . "0") '(10 0.0 0.0 0.0))))
        (pl:fail "无法创建自定义图例包装块。"))
      (if (not (entmake (list '(0 . "INSERT") (cons 2 source) '(8 . "0") '(62 . 0)
        '(10 0.0 0.0 0.0) '(41 . 1.0) '(42 . 1.0) '(43 . 1.0) '(50 . 0.0))))
        (pl:fail "无法引用自定义图例。"))
      (pl:symbol-attdefs) (entmake '((0 . "ENDBLK") (8 . "0")))))
  name)
(defun pl:symbol-state (e p units opts / ed child attrs)
  (setq ed (entget e))
  (if (= (cdr (assoc 66 ed)) 1)
    (progn
      (setq child (entnext e))
      (while (and child (/= (cdr (assoc 0 (entget child))) "SEQEND"))
        (setq attrs (cons (entget child) attrs) child (entnext child)))))
  (list p units opts ed attrs))
(defun pl:symbol-attribute (tag p pos height opts / point text hidden)
  (cond
    ((= tag "PL_NAME") (setq text (pl:get 'name p)
      point (if (= (pl:get 'kind p) 3) pos (list (car pos) (+ (cadr pos) (* 0.75 height)) (caddr pos)))))
    ((= tag "PL_DIAMETER") (setq text (if (= (pl:get 'kind p) 3) "" (pl:dbh-text p 0 nil))
      point (list (car pos) (- (cadr pos) (* 0.75 height)) (caddr pos))))
    ((= tag "PL_SPEC") (setq text (pl:get 'spec_no p)
      point (list (car pos) (- (cadr pos) (* 2.25 height)) (caddr pos))
      hidden (or (member (pl:get 'kind p) '(0 3)) (/= (pl:get 'show_number opts) 1)))))
  (if text (list text point (or (= text "") hidden))))
(defun pl:refresh-symbol (e / p obj attrs attr tag units opts height scale pos text point no state values)
  (setq p (pl:plant e))
  (if (and p (pl:writable e) (setq units (pl:data-get e "UNITS")))
    (progn
      (setq opts (pl:db-get "PLOT_OPTIONS" '((scale . 100.0) (paper_height . 2.5) (show_number . 0)))
        state (pl:symbol-state e p units opts))
      (if (equal state (pl:get e pl:*symbol-states*)) T
      (progn
      (setq obj (vlax-ename->vla-object e) attrs (vlax-invoke obj 'GetAttributes)
            scale (if (= (cdr (assoc 67 (entget e))) 1) 1.0 (pl:get 'scale opts))
            height (pl:paper-height (pl:get 'paper_height opts) scale units)
            pos (trans (cdr (assoc 10 (entget e))) e 0)
            no (pl:get 'spec_no p))
      (foreach attr attrs
        (setq tag (strcase (vla-get-TagString attr)) values (pl:symbol-attribute tag p pos height opts)
          text (car values) point (cadr values))
        (if text
          (progn
            (vla-put-TextString attr text) (vla-put-Height attr height)
            (vla-put-Color attr 7) (vla-put-Rotation attr 0.0) (vla-put-Alignment attr 10)
            (vla-put-TextAlignmentPoint attr (vlax-3d-point point))
            (vla-put-Invisible attr (if (caddr values)
              :vlax-true :vlax-false)) (vla-Update attr))))
      (vla-Update obj)
      (if attrs (progn (setq pl:*symbol-states* (pl:put e (pl:symbol-state e p units opts) pl:*symbol-states*)) T) nil)))) nil))
(defun pl:refresh-all-symbols (/ e n result skipped errors)
  (setq n 0 skipped 0 errors 0)
  (foreach e (pl:all-trees)
    (setq result (vl-catch-all-apply 'pl:refresh-symbol (list e)))
    (cond
      ((vl-catch-all-error-p result) (setq errors (1+ errors))
        (princ (strcat "\n文字刷新失败：" (vl-catch-all-error-message result))))
      (result (setq n (1+ n))) (T (setq skipped (1+ skipped)))))
  (princ (strcat "\n图块内文字刷新 " (itoa n) " 个；旧版无属性或锁定 " (itoa skipped)
    " 个；失败 " (itoa errors) " 个。")) n)

(defun pl:physical-key (p)
  (list (pl:normal-name (pl:get 'name p)) (pl:get 'kind p)
    (pl:get 'dbh p) (pl:get 'caliper p) (pl:get 'height p)
    (pl:get 'crown p) (pl:get 'quantity_unit p)))
(defun pl:instance-variant (p / row existing)
  (foreach row (pl:defs)
    (if (equal (pl:physical-key row) (pl:physical-key p)) (setq existing row)))
  (if existing
    (setq p (pl:put 'id (pl:get 'id existing) p)
          p (pl:put 'spec_no (pl:get 'spec_no existing) p))
    (progn
      (setq p (pl:put 'id (pl:new-id) p)
            p (pl:put 'spec_no (pl:next-spec-number (pl:used-specs)) p))
      (pl:save-def p))) p)
(defun pl:symbol-copy-work (/ p source name blocks target objects obj array)
  (setq p (pl:current))
  (if (not p) (alert "先用 PLPLANT 选择一个项目规格。")
    (progn
      (pl:built-blocks)
      (setq source (if (= (pl:get 'style p) 2) (pl:get 'block p) (pl:block-name p))
            name (pl:trim (getstring T "\n新图例图块名称：")))
      (cond
        ((or (= name "") (not (snvalid name))) (alert "图块名称为空或不合法。"))
        ((tblsearch "BLOCK" name) (alert "该图块名称已存在，请使用新名称。"))
        (T
          (setq blocks (vla-get-Blocks (pl:doc)) target (vla-Add blocks (vlax-3d-point '(0.0 0.0 0.0)) name)
                objects nil)
          (vlax-for obj (vla-Item blocks source)
            (if (/= (vla-get-ObjectName obj) "AcDbAttributeDefinition") (setq objects (cons obj objects))))
          (if objects
            (progn
              (setq array (vlax-make-safearray vlax-vbObject (cons 0 (1- (length objects)))))
              (vlax-safearray-fill array (reverse objects))
              (vla-CopyObjects (pl:doc) (vlax-make-variant array) target)
              (setq p (pl:put 'base (if (= (pl:get 'style p) 2) (pl:get 'base p) 1.0) p)
                    p (pl:put 'block name p) p (pl:put 'style 2 p))
              (pl:save-def p)
              (princ (strcat "\n已为当前规格建立图例副本：" name
                "。用 BEDIT 修改外框；修改外径后，在规格中同步填写基准直径。已有植物用 PLUPDATE 应用。")))
            (alert "源图例为空。")))))))
(defun c:PLANTCADDESIGN () (pl:run 'pl:design-start))
(defun c:PLANTCADCATALOG () (pl:run 'pl:design-start))
(defun c:PLANTCADSYMBOL () (pl:run 'pl:symbol-copy-work))
(defun c:PLANTCADCATSAVE () (pl:run 'pl:catalog-export))
(defun c:PLANTCADCATLOAD () (pl:run 'pl:catalog-import))
(princ)

;;; Reserve past specification numbers so existing snapshots keep unambiguous IDs.
(defun pl:used-specs () (append (pl:defs) (pl:db-get "SPEC_HISTORY" nil)))
(defun pl:history-error (p / previous row no)
  (setq no (strcase (pl:get 'spec_no p)) previous nil)
  (foreach row (pl:db-get "SPEC_HISTORY" nil)
    (if (= no (strcase (pl:get 'spec_no row))) (setq previous row)))
  (if (and previous (not (equal (pl:physical-key p) (pl:physical-key previous))))
    "这个编号已用于其他真实规格，请使用新编号。" nil))
(defun pl:remember-spec (p / history row old msg)
  (setq history (pl:db-get "SPEC_HISTORY" nil) old nil)
  (if (setq msg (pl:history-error p)) (pl:fail msg))
  (foreach row history
    (if (= (strcase (pl:get 'spec_no row)) (strcase (pl:get 'spec_no p))) (setq old row)))
  (if (not old) (pl:db-put "SPEC_HISTORY" (append history (list p)))) p)
(defun pl:prepare-edited-spec (p old defs)
  ;; The old argument is the dialog snapshot; fresh variants start with a fresh ID.
  (if (and (pl:get 'spec_no old) (/= (pl:get 'spec_no old) "")
           (= (strcase (pl:get 'spec_no p)) (strcase (pl:get 'spec_no old)))
           (not (equal (pl:physical-key p) (pl:physical-key old)))
           (pl:by-id (pl:get 'id p)))
    (setq p (pl:put 'id (pl:new-id) (pl:put 'spec_no (pl:next-spec-number defs) p)))) p)

;;; Optional visual sample; invoked by the designer only in an empty model.
(defun pl:demo-insert (p point / units scale obj e)
  (setq units 1000.0 scale (pl:block-scale p units))
  (setq obj (vla-InsertBlock (vla-get-ModelSpace (pl:doc)) (vlax-3d-point point)
    (pl:block-name p) scale scale scale 0.0))
  (vla-put-Layer obj (pl:tree-layer p)) (vla-put-Color obj 256)
  (setq e (vlax-vla-object->ename obj))
  (pl:mark e "TREE" nil) (pl:data-put e "PLANT" p) (pl:data-put e "UNITS" units)
  (if (not (pl:refresh-symbol e)) (pl:fail "示例图块缺少文字属性。")) e)
(defun pl:demo-work (/ p q r)
  (if (or (> (vla-get-Count (vla-get-ModelSpace (pl:doc))) 0) (pl:defs))
    (pl:fail "PLDEMO只用于新建空白图，请先另建空白图再运行。"))
  (pl:init-layers) (pl:built-blocks) (pl:db-put "UNIT" 0)
  (pl:db-put "PLOT_OPTIONS" '((scale . 100.0) (paper_height . 2.5) (show_number . 0)))
  (setq p (pl:new-spec nil) p (pl:put 'name "银杏" p)
    p (pl:put 'dbh 12.0 p) p (pl:put 'height 4.0 p) p (pl:put 'crown 3.0 p))
  (pl:save-def p)
  (setq q (pl:put 'id (pl:new-id) p) q (pl:put 'spec_no (pl:next-spec-number (pl:used-specs)) q)
    q (pl:put 'dbh 18.0 q) q (pl:put 'height 5.0 q) q (pl:put 'crown 5.0 q))
  (pl:save-def q)
  (setq r (pl:new-spec nil) r (pl:put 'name "桂花" r)
    r (pl:put 'caliper 8.0 r) r (pl:put 'diameter_mode 1 r)
    r (pl:put 'height 3.0 r) r (pl:put 'crown 3.0 r) r (pl:put 'style 1 r))
  (pl:save-def r)
  (pl:demo-insert p '(0.0 0.0 0.0))
  (pl:demo-insert q '(7000.0 0.0 0.0))
  (pl:demo-insert r '(14000.0 0.0 0.0))
  (pl:db-put "CURRENT" (pl:get 'id p))
  (if (= (vla-get-Visible (vlax-get-acad-object)) :vlax-true)
    (vla-ZoomExtents (vlax-get-acad-object)))
  (princ "\n已生成3个示例：银杏D12/P3、银杏D18/P5、桂花地径8/P3。")
  (princ "\n字高250mm，按1:100出图为2.5mm。用PLINFO查看编号，PLSET改比例，PLTABLE生成规格表。"))
(defun c:PLANTCADDEMO () (pl:run 'pl:demo-work))

;;; Dedicated tables for selected plants and project specifications.
(defun pl:design-table-work (layer title headers rows)
  (pl:output-table-create layer (if (= layer "PL_表格_植物名录") "list" "specs") title))
(defun pl:legacy-design-table-work (layer title headers rows / opts scale height defaultheight point table row value col i)
  (pl:init-layers)
  (if (not (pl:layer-open layer)) (pl:fail "目标表格图层已锁定，请先解锁。"))
  (if (not rows) (princ "\n请先用PLDESIGN选择植物并建立项目规格。")
    (if (pl:require-units)
      (progn
        (setq opts (pl:db-get "PLOT_OPTIONS" '((scale . 100.0))))
        (setq scale (if (and (= (getvar "TILEMODE") 0) (= (getvar "CVPORT") 1))
                      1.0 (pl:get 'scale opts)))
        (setq defaultheight (pl:paper-height 2.5 scale (pl:units)))
        (initget 6)
        (setq height (getreal (strcat "\n表格字高 / cm <" (pl:num (/ (* defaultheight 100.0) (pl:units))) ">：")))
        (if height (setq height (* (/ height 100.0) (pl:units))) (setq height defaultheight))
        (if (setq point (getpoint (strcat "\n" title "插入点：")))
          (progn
            (setq table (vla-AddTable (pl:space) (vlax-3d-point (trans point 1 0))
              (+ 2 (length rows)) (length headers) (* 2 height) (* 16 height)))
            (vla-put-Layer table layer)
            (vla-SetTextHeight table 7 height)
            (vla-SetTextStyle table 7 (getvar "TEXTSTYLE"))
            (vla-SetText table 0 0 title)
            (setq col 0)
            (foreach value headers
              (vla-SetText table 1 col value) (setq col (1+ col)))
            (setq i 2)
            (foreach row rows
              (setq col 0)
              (foreach value row
                (vla-SetText table i col value) (setq col (1+ col)))
              (setq i (1+ i)))
            (pl:mark (vlax-vla-object->ename table) "TABLE" nil)
            (princ (strcat "\n已在 " layer " 生成表格快照，植物或规格修改后请重新生成。"))))))))
(defun pl:list-table-work ()
  (pl:design-table-work "PL_表格_植物名录" "植物名录表（项目选定品种）"
    '("序号" "植物名称" "形态分类" "参考地区")
    (pl:plant-list-rows (pl:ai-visible-defs) (pl:catalog))))
(defun pl:spec-table-work ()
  (pl:design-table-work "PL_表格_植物规格" "植物规格表（项目定义）"
    '("规格编号" "植物名称" "类别" "胸径 cm" "地径 cm" "高度 cm" "冠幅 cm" "单位")
    (pl:spec-list-rows (pl:ai-visible-defs))))
(defun c:PLANTCADLISTTABLE () (pl:run 'pl:list-table-work))
(defun c:PLANTCADSPECTABLE () (pl:run 'pl:spec-table-work))

;;; Register a short alias only when no other add-on owns it.
(pl:register-command "PLDESIGN" "PLANTCADDESIGN")
(pl:register-command "PLCATALOG" "PLANTCADCATALOG")
(pl:register-command "PLSYMBOL" "PLANTCADSYMBOL")
(pl:register-command "PLCATSAVE" "PLANTCADCATSAVE")
(pl:register-command "PLCATLOAD" "PLANTCADCATLOAD")
(pl:register-command "PLDEMO" "PLANTCADDEMO")
(pl:register-command "PLLISTTABLE" "PLANTCADLISTTABLE")
(pl:register-command "PLSPECTABLE" "PLANTCADSPECTABLE")

(defun pl:remember-size (p / defaults old values key)
  (setq defaults (pl:db-get "SIZE_DEFAULTS" nil) values nil)
  (foreach key '(crown height dbh caliper diameter_mode)
    (setq values (append values (list (cons key (pl:get key p))))))
  (setq old (assoc (pl:size-key p) defaults))
  (pl:db-put "SIZE_DEFAULTS" (if old (subst (cons (pl:size-key p) values) old defaults)
    (append defaults (list (cons (pl:size-key p) values))))))

(defun pl:project-columns ()
  (strcat "分类\t编号\t植物名称\t高度H/cm\t冠幅P/cm\t胸径D/cm\t地径d/cm\t单位"))
(defun pl:project-list-row (p)
  (strcat (pl:kind-name (pl:get 'kind p)) "\t" (pl:get 'spec_no p) "\t" (pl:get 'name p)
    "\t" (pl:dimension-text 'height p) "\t" (pl:dimension-text 'crown p)
    "\t" (pl:dimension-text 'dbh p) "\t" (pl:dimension-text 'caliper p) "\t" (pl:get 'quantity_unit p)))
(defun pl:project-filter-dialog (/ row key)
  (setq pl:*project-visible* (pl:project-filter (pl:defs) (1- (atoi (get_tile "project_kind"))) (get_tile "project_query")))
  (start_list "project_columns") (add_list (pl:project-columns)) (end_list)
  (start_list "plants")
  (foreach row pl:*project-visible*
    (add_list (pl:project-list-row row)))
  (end_list) (setq pl:*index* 0)
  (foreach key '("edit" "clone" "update" "accept" "place") (mode_tile key (if pl:*project-visible* 0 1)))
  (if pl:*project-visible* (set_tile "plants" "0")))
(defun pl:calibrate-work (/ first second actual units)
  (princ "\n选底图上已知真实长度的两点；例如标注为500cm的边，不用文字高度推断单位。")
  (if (and (setq first (getpoint "\n校准起点：")) (setq second (getpoint first "\n校准终点：")))
    (progn
      (initget 6) (setq actual (getreal "\n这段距离的真实长度 / cm："))
      (if (setq units (pl:calibrated-units (distance first second) actual))
        (progn (pl:db-put "UNITS_PER_M" units) (pl:db-put "UNIT" 3)
          (princ (strcat "\n已校准：1米=" (pl:num units) "图纸单位。应用于接下来布置和识别的区域；已有对象保留其原单位记录。")))
        (princ "\n校准未完成，原单位设置保留。")))))
(defun pl:save-info-work ()
  (alert (strcat "植物品种、项目规格、待选清单和尺寸记忆保存在DWG图纸内部。\n"
    "图中植物和面积对象另外保存各自的规格、单位和关联标注。\n\n"
    (if (= (getvar "DWGTITLED") 1) (strcat "保存文件：" (getvar "DWGPREFIX") (getvar "DWGNAME"))
      "当前图纸尚未命名，请先另存为DWG。")
    "\n\n点击“保存项目到当前DWG”或按CAD原生Ctrl+S。仅关闭植物浮窗不会清除项目。")))
(defun pl:save-project-work ()
  (if (= (getvar "DWGTITLED") 1) (progn (vla-Save (pl:doc)) (princ "\n项目植物信息已随当前DWG保存。"))
    (command "_.QSAVE")))
(defun c:PLANTCADCALIBRATE () (pl:run 'pl:calibrate-work))
(defun c:PLANTCADSAVEINFO () (pl:save-info-work) (princ))
(defun c:PLANTCADSAVE () (pl:save-project-work) (princ))

(defun pl:project-size-defaults (/ defaults p values key)
  (setq defaults (pl:db-get "SIZE_DEFAULTS" nil))
  (foreach p (pl:defs)
    (if (not (assoc (pl:size-key p) defaults))
      (progn (setq values nil)
        (foreach key '(crown height dbh caliper diameter_mode) (setq values (append values (list (cons key (pl:get key p))))))
        (setq defaults (append defaults (list (cons (pl:size-key p) values))))))) defaults)
