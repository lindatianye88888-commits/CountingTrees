;;; PlantCAD III: floating workbench workflows. Pure geometry comes first.
(defun pl:line-stations (extent spacing closed / result d epsilon)
  (if (and (numberp extent) (numberp spacing) (> extent 0.0) (> spacing 0.0)
           (<= (/ extent spacing) 1999.0))
    (progn
      (setq result nil d 0.0 epsilon (* 1.0e-10 (max 1.0 extent)))
      (while (if closed (< d (- extent epsilon)) (<= d (+ extent epsilon)))
        (setq result (cons (min d extent) result) d (+ d spacing)))
      (reverse result)) nil))

(defun pl:polygon-bounds (points / lo-x lo-y hi-x hi-y pt)
  (setq lo-x (caar points) hi-x lo-x lo-y (cadar points) hi-y lo-y)
  (foreach pt points
    (setq lo-x (min lo-x (car pt)) hi-x (max hi-x (car pt))
          lo-y (min lo-y (cadr pt)) hi-y (max hi-y (cadr pt))))
  (list lo-x lo-y hi-x hi-y))

(defun pl:orient (a b p)
  (- (* (- (car b) (car a)) (- (cadr p) (cadr a)))
     (* (- (cadr b) (cadr a)) (- (car p) (car a)))))

(defun pl:on-segment (p a b / epsilon)
  (setq epsilon (* 1.0e-9 (max 1.0 (abs (- (car b) (car a))) (abs (- (cadr b) (cadr a))))))
  (and (<= (abs (pl:orient a b p)) epsilon)
       (<= (- (min (car a) (car b)) epsilon) (car p))
       (<= (car p) (+ (max (car a) (car b)) epsilon))
       (<= (- (min (cadr a) (cadr b)) epsilon) (cadr p))
       (<= (cadr p) (+ (max (cadr a) (cadr b)) epsilon))))

(defun pl:segments-touch (a b c d / ab-c ab-d cd-a cd-b)
  (setq ab-c (pl:orient a b c) ab-d (pl:orient a b d)
        cd-a (pl:orient c d a) cd-b (pl:orient c d b))
  (or (and (< (* ab-c ab-d) 0.0) (< (* cd-a cd-b) 0.0))
      (pl:on-segment c a b) (pl:on-segment d a b)
      (pl:on-segment a c d) (pl:on-segment b c d)))

(defun pl:polygon-area (points / previous pt sum origin)
  (setq previous (last points) origin (car points) sum 0.0)
  (foreach pt points
    (setq sum (+ sum (pl:orient origin previous pt))
          previous pt))
  (/ (abs sum) 2.0))

(defun pl:simple-polygon (points / n i j good a b)
  (setq n (length points) good (and (>= n 3) (<= n 512) (> (pl:polygon-area points) 1.0e-12)) i 0)
  (while (and good (< i n))
    (setq a (nth i points) b (nth (rem (1+ i) n) points) j (1+ i))
    (if (equal a b 1.0e-9) (setq good nil))
    (while (and good (< j n))
      (if (and (/= j (1+ i)) (not (and (= i 0) (= j (1- n))))
               (pl:segments-touch a b (nth j points) (nth (rem (1+ j) n) points)))
        (setq good nil))
      (setq j (1+ j)))
    (setq i (1+ i))) good)

(defun pl:inside-polygon (point points / previous pt inside boundary y)
  (setq previous (last points) inside nil boundary nil y (cadr point))
  (foreach pt points
    (if (pl:on-segment point previous pt) (setq boundary T))
    (if (or (and (> (cadr pt) y) (<= (cadr previous) y))
            (and (> (cadr previous) y) (<= (cadr pt) y)))
      (if (< (car point) (+ (car pt) (* (- y (cadr pt))
                   (/ (- (car previous) (car pt)) (- (cadr previous) (cadr pt))))))
        (setq inside (not inside))))
    (setq previous pt))
  (or boundary inside))

(defun pl:polygon-grid (points spacing / box x y nx ny out point)
  (if (and (> spacing 0.0) (pl:simple-polygon points))
    (progn
      (setq box (pl:polygon-bounds points)
            nx (1+ (fix (/ (- (nth 2 box) (car box)) spacing)))
            ny (1+ (fix (/ (- (nth 3 box) (cadr box)) spacing))))
      (if (> (* nx ny) 10000) 'limit
        (progn
          (setq y (+ (cadr box) (/ spacing 2.0)) out nil)
          (while (< y (nth 3 box))
            (setq x (+ (car box) (/ spacing 2.0)))
            (while (< x (nth 2 box))
              (setq point (list x y))
              (if (pl:inside-polygon point points) (setq out (cons point out)))
              (setq x (+ x spacing)))
            (setq y (+ y spacing)))
          (reverse out)))) nil))

(defun pl:add-quantity (p quantity rows / key row)
  (setq key (pl:count-key p) row (assoc key rows))
  (if row (subst (list key (cadr row) (+ quantity (caddr row))) row rows)
    (append rows (list (list key p quantity)))))

;;; Host operations. All public workflows execute inside pl:run's single undo mark.
(defun pl:work-plant (/ p issue)
  (pl:init-layers)
  (if (not (pl:current)) (pl:design-start))
  (setq p (pl:current))
  (if p (setq p (pl:resolve-placement p)))
  (if (and p (pl:require-units))
    (progn
      (if (setq issue (pl:insert-error p)) (pl:fail issue))
      (pl:built-blocks)
      (if (setq issue (pl:layer-issue (pl:tree-layer p))) (pl:fail issue)) p) nil))

(defun pl:plant-at (p point / obj e units)
  (setq units (pl:units) obj (pl:insert-symbol p point (pl:block-scale p units))
        e (vlax-vla-object->ename obj))
  (pl:mark e "TREE" nil)
  (pl:data-put e "PLANT" p) (pl:data-put e "UNITS" units)
  (if (not (pl:refresh-symbol e)) (pl:fail "图块文字创建失败，请检查图例。"))
  e)

(defun pl:annotation-plant (e / source p)
  (cond ((setq p (pl:plant e)) p)
    ((and (equal (pl:role e) "AREA") (setq p (pl:data-get e "AREA_PLANT"))) p)
    ((and (member (pl:role e) '("LABEL" "LEADER" "AREA_LABEL" "AREA_LEADER" "AREA_ARROW" "AREA_FILL")) (setq source (pl:source e)))
      (if (equal (pl:role source) "AREA") (pl:data-get source "AREA_PLANT") (pl:plant source)))
    (T nil)))

(defun pl:label-plant-matches (lines defs / names specs p line named numbered)
  ;; A specification number disambiguates different sizes of the same species.
  (foreach p defs
    (setq named nil numbered nil)
    (foreach line lines
      (if (equal (pl:normal-name line) (pl:normal-name (pl:get 'name p))) (setq named T))
      (if (and (/= (pl:get 'spec_no p) "") (equal (pl:normal-name line) (pl:normal-name (pl:get 'spec_no p)))) (setq numbered T)))
    (if named (setq names (append names (list p))))
    (if numbered (setq specs (append specs (list p)))))
  (if specs specs names))

(defun pl:plant-from-picked-annotation (e / p lines matches)
  (if (setq p (pl:annotation-plant e)) p
    (if (and (boundp 'pl:*native-ui*) pl:*native-ui*)
      (progn
        (setq lines (pl:native-label-lines (cdr (assoc 5 (entget e))))
          matches (pl:label-plant-matches lines (pl:defs)))
        (if (= (length matches) 1) (car matches)
          (progn
            (alert "此标注未匹配到唯一的项目植物规格。请到“项目规格”选定品种，再用“编辑→已算面积关联当前植物”。普通文字请使用完整植物名称或规格编号；天正自定义对象可能需要先选择其中的文字。") nil))) nil)))

(defun pl:make-current-plant (p)
  (setq p (pl:upgrade-plant p))
  (if (not (equal (pl:by-id (pl:get 'id p)) p)) (setq p (pl:instance-variant p)))
  (pl:save-def p) (pl:db-put "CURRENT" (pl:get 'id p))
  (princ (strcat "\n当前植物：" (pl:get 'name p) " / " (pl:get 'spec_no p))) p)

(defun pl:pick-current-work (/ pick p)
  (if (setq pick (entsel "\n选择已有植物、品种标注或已关联的面积文字："))
    (if (setq p (pl:plant-from-picked-annotation (car pick)))
      (progn (pl:make-current-plant p) T) nil)))

(defun pl:reuse-work () (if (pl:pick-current-work) (pl:insert-work)))

(defun pl:set-style-work (style / p)
  (setq p (pl:current))
  (if (not p) (pl:design-start))
  (if (setq p (pl:current))
    (progn (setq p (pl:put 'style style p)) (pl:save-def p)
      (princ "\n当前图例已切换；已有植物可用“按当前定义批量更新”同步。"))))

(defun pl:circle-work () (pl:set-style-work 0))
(defun pl:simple-work () (pl:set-style-work 1))

(defun pl:block-pick-work (/ p pick ed name issue result)
  (if (not (pl:current)) (pl:design-start))
  (if (and (setq p (pl:current)) (setq pick (entsel "\n选择一个普通图块作为当前植物图例：")))
    (progn
      (setq ed (entget (car pick)) name (cdr (assoc 2 ed)))
      (cond
        ((/= (cdr (assoc 0 ed)) "INSERT") (alert "请选择普通图块参照。"))
        ((or (pl:plant (car pick)) (not name) (= (substr name 1 1) "*")) (alert "请选择不带属性的普通图块，不使用植物包装块或匿名动态块。"))
        ((setq issue (pl:custom-error name)) (alert issue))
        (T
          (setq p (pl:put 'block name (pl:put 'style 2 p)))
          (if (setq result (pl:edit-dialog p))
            (progn (pl:save-def result) (pl:db-put "CURRENT" (pl:get 'id result)))))))))

(defun pl:line-work (/ p pick curve result path-length spacing stations station point n)
  (if (setq p (pl:work-plant))
    (if (setq pick (entsel "\n选择布置路径（直线、圆弧或多段线）："))
      (progn
        (setq curve (car pick) result (vl-catch-all-apply 'vlax-curve-getEndParam (list curve)))
        (if (vl-catch-all-error-p result) (pl:fail "所选对象不是可用的曲线。"))
        (setq path-length (vlax-curve-getDistAtParam curve result))
        (initget 6)
        (if (setq spacing (getreal "\n输入株距 / cm："))
          (progn
            (setq stations (pl:line-stations path-length (* (/ spacing 100.0) (pl:units)) (vlax-curve-isClosed curve)))
            (if (not stations) (pl:fail "路径长度或间距无效，或一次超过2000株；请调整间距或分段布置。"))
            (setq n 0)
            (foreach station stations
              (setq point (vlax-curve-getPointAtDist curve station))
              (pl:plant-at p point) (setq n (1+ n)))
            (princ (strcat "\n沿线布置完成：" (itoa n) " 株；原路径保留。"))))))))

(defun pl:boundary-data (e / ed points pair curved normal elevation)
  (setq ed (entget e) points nil curved nil normal (cdr (assoc 210 ed)))
  (if (and (= (cdr (assoc 0 ed)) "LWPOLYLINE")
           (/= 0 (logand 1 (cdr (assoc 70 ed))))
           (or (not normal) (equal normal '(0.0 0.0 1.0) 1.0e-9)))
    (progn
      (foreach pair ed
        (if (= (car pair) 10) (setq points (cons (cdr pair) points)))
        (if (and (= (car pair) 42) (/= (cdr pair) 0.0)) (setq curved T)))
      (setq points (reverse points) elevation (if (assoc 38 ed) (cdr (assoc 38 ed)) 0.0))
      (if (and (not curved) (pl:simple-polygon points)) (list points elevation) nil)) nil))

(defun pl:pick-boundary (/ pick boundary)
  (if (setq pick (entsel "\n选择闭合直线段轻量多段线边界（保留原线）："))
    (if (setq boundary (pl:boundary-data (car pick))) boundary
      (progn (alert "需要无自交的闭合二维轻量多段线，最多512个顶点。本版边界暂不接受圆弧段、孔洞或倾斜平面。") nil))))

(defun pl:grid-work (/ p boundary spacing points point n)
  (if (and (setq p (pl:work-plant)) (setq boundary (pl:pick-boundary)))
    (progn
      (initget 6)
      (if (setq spacing (getreal "\n网格横向与纵向间距 / cm："))
        (progn
          (setq points (pl:polygon-grid (car boundary) (* (/ spacing 100.0) (pl:units))))
          (cond
            ((eq points 'limit) (pl:fail "网格候选点超过10000个，请增大间距或分区布置。"))
            ((not points) (alert "该间距下边界内没有网格点，请减小间距。"))
            (T
              (setq n 0)
              (foreach point points
                (pl:plant-at p (list (car point) (cadr point) (cadr boundary)))
                (setq n (1+ n)))
              (princ (strcat "\n区域布置完成：" (itoa n) " 株；原边界保留。")))))))))

(defun pl:area-number (e / no)
  (setq no (pl:data-get e "AREA_NO"))
  (if no no (strcat "A" (cdr (assoc 5 (entget e))))))
(defun pl:area-title (e / p)
  (if (setq p (pl:data-get e "AREA_PLANT")) (pl:get 'name p)
    (strcat "区域 " (pl:area-number e))))
(defun pl:register-geometric-area (e kind / sequence)
  ;; Geometry is valid without a species. Never inherit the current plant implicitly.
  (setq sequence (1+ (pl:db-get "AREA_SEQUENCE" 0)))
  (pl:db-put "AREA_SEQUENCE" sequence)
  (pl:mark e "AREA" nil)
  (pl:data-put e "AREA_NO" (strcat "A" (itoa sequence)))
  (pl:data-put e "AREA_KIND" kind)
  (pl:data-put e "UNITS" (pl:units)) e)
(defun pl:consume-area-row (row kind / e point fresh radius label text ed)
  (if (and (setq e (handent (car row))) (entget e) (setq point (pl:point-value (cadr row))))
    (progn
      (setq fresh (not (pl:data-get e "AREA_NO")))
      (if fresh
        (progn (pl:register-geometric-area e kind) (pl:data-put e "AREA_REPAIRED" (nth 2 row))))
      (if (equal (nth 4 row) 1) (pl:data-put e "AREA_FITTED" 1))
      (setq radius (nth 3 row))
      (pl:data-put e "AREA_LABEL_RADIUS" radius)
      (setq label (cdr (assoc e pl:*measure-labels*)))
      (if (and label (entget label))
        (progn
          (if (not (pl:writable label)) (pl:fail "已有面积文字图层锁定，未移动或覆盖。"))
          (setq text (pl:area-label-text e) ed (pl:set-dxf 10 point (pl:set-dxf 1 text (entget label))))
          (if (not (equal ed (entget label))) (if (entmod ed) (entupd label) (pl:fail "面积文字更新失败。")))
          "KEPT")
        (if (setq label (pl:create-area-label e point))
          (progn (setq pl:*measure-labels* (cons (cons e label) pl:*measure-labels*)) "CREATED")
          (pl:fail "区域已登记，但面积文字未生成，请检查面积值和标注图层。"))))
    (pl:fail "区域返回了无效句柄或区内标注点。")))
(defun pl:consume-area-batch (result kind / row label source answer previous created kept failed n)
  (if (not (and (listp result) (equal (car result) "AREA_BATCH")))
    (pl:fail (if (= (type (pl:native-value result)) 'STR) (pl:native-value result) "自动面积返回格式无效。")))
  (setq pl:*measure-labels* nil created 0 kept 0 failed 0 n 0)
  (foreach label (pl:all-labels)
    (if (and (= (cdr (assoc 0 (entget label))) "MTEXT") (equal (pl:role label) "AREA_LABEL")
      (not (pl:data-get label "OUTPUT_OPTIONS")) (setq source (pl:source label)))
      (setq pl:*measure-labels* (cons (cons source label) pl:*measure-labels*))))
  (foreach row (cdr result)
    (setq previous pl:*failure* pl:*failure* nil
      answer (vl-catch-all-apply 'pl:consume-area-row (list row kind)))
    (if (vl-catch-all-error-p answer)
      (progn (setq failed (1+ failed))
        (princ (strcat "\n区域 " (car row) " 面积文字未完成："
          (if pl:*failure* pl:*failure* (vl-catch-all-error-message answer)) "；可用“手动补面积”处理。")))
      (progn (setq n (1+ n))
        (if (equal answer "CREATED") (setq created (1+ created)) (setq kept (1+ kept)))))
    (setq pl:*failure* previous))
  (setq pl:*measure-labels* nil)
  (princ (strcat "\n已检查 " (itoa n) " 个区域；新增面积文字 " (itoa created)
    " 个；保留/更新已有文字 " (itoa kept) " 个；未完成 " (itoa failed) " 个。")) n)
(defun pl:range-session-loop (/ result layer)
  (setq layer (cond ((= pl:*range-kind* 1) "PL_灌木_计算边界")
    ((= pl:*range-kind* 2) "PL_草地_边界") (T "PL_面积_计算边界")))
  (if (pl:layer-issue layer) (pl:fail (pl:layer-issue layer)))
  (if (pl:layer-issue "PL_标注_区域") (pl:fail (pl:layer-issue "PL_标注_区域")))
  (setq result (pl:native-area-export-all layer))
  (pl:consume-area-batch result pl:*range-kind*))

(defun pl:manual-area-work (/ mode pick entity selection handles result)
  (if (not (and (boundp 'pl:*native-ui*) pl:*native-ui*)) (pl:fail "手动补面积需要配套原生插件。"))
  (if (pl:require-units)
    (progn
      (pl:init-layers)
      (if (pl:layer-issue "PL_面积_计算边界") (pl:fail (pl:layer-issue "PL_面积_计算边界")))
      (if (pl:layer-issue "PL_标注_区域") (pl:fail (pl:layer-issue "PL_标注_区域")))
      (initget "Boundary Edges")
      (setq mode (getkword "\n手动补面积 [点闭合边界(Boundary)/框选组成边线(Edges)] <Boundary>："))
      (cond
        ((equal mode "Edges")
          (princ "\n框选组成围合的全部边线，可跨图层；只计算实际闭合，不猜测补线。")
          (setq selection (ssget '((0 . "LINE,ARC,LWPOLYLINE,POLYLINE,SPLINE,CIRCLE,ELLIPSE"))))
          (foreach entity (pl:ss-list selection) (setq handles (cons (cdr (assoc 5 (entget entity))) handles)))
          (if handles (pl:consume-area-batch (pl:native-area-manual (reverse handles) "PL_面积_计算边界") -1)))
        (T
          (while (setq pick (entsel "\n点选闭合多段线、圆、椭圆或计算面域（回车结束）："))
            (setq entity (or (pl:area-from-selection (car pick)) (car pick))
              result (pl:native-area-manual (list (cdr (assoc 5 (entget entity)))) "PL_面积_计算边界"))
            (if (and (listp result) (equal (car result) "AREA_BATCH")) (pl:consume-area-batch result -1)
              (princ (strcat "\n" (pl:native-value result) "；散线请用框选组成边线方式。")))))))))
(defun pl:area-selection (/ filter selection handles index)
  (setq pl:*stage* "选择面积边界"
    filter '((0 . "LINE,ARC,LWPOLYLINE,POLYLINE,SPLINE,CIRCLE,ELLIPSE")))
  (setq selection (ssget "_I" filter))
  (if (not selection)
    (progn
      (princ "\n框选灌木边线，框选完成后按回车开始计算；Esc 取消。其他图层可以保持显示。")
      (setq selection (ssget filter))))
  (if selection
    (progn
      (setq handles nil index 0)
      (repeat (sslength selection)
        (setq handles (cons (cdr (assoc 5 (entget (ssname selection index)))) handles) index (1+ index)))
      (sssetfirst nil nil)
      (reverse handles))
    (progn (princ "\n未选择边界，面积识别已取消。") nil)))

(defun pl:area-prepare (handles / count picked layer)
  (setq pl:*stage* "计算边线围合面积"
    count (pl:native-value (pl:native-area-begin handles "")))
  (if (equal count "AREA_PICK_LAYER")
    (progn
      (setq pl:*stage* "确认灌木边线图层"
        picked (entsel "\n点选框选范围内的一条灌木边线确认图层（Esc 取消）："))
      (if picked
        (progn
          (setq layer (cdr (assoc 8 (entget (car picked)))) pl:*stage* "计算边线围合面积"
            count (pl:native-value (pl:native-area-begin handles layer))))
        (setq count nil))))
  (if (= (type count) 'STR) (pl:fail count)) count)

(defun pl:geometry-session-work (/ handles count total)
  ;; Finish native CAD selection before invoking geometry. Units convert only after calculation.
  (if (and (setq handles (pl:area-selection)) (setq count (pl:area-prepare handles)))
    (if (and (numberp count) (> count 0) (pl:require-units))
      (progn
        (setq pl:*stage* "生成区域和面积标注")
        (pl:init-layers)
        (setq total (pl:native-value (pl:native-area-total)))
        (if (numberp total) (princ (strcat "\n候选闭合区域合计：" (rtos (/ total (* (pl:units) (pl:units))) 2 2)
          " 平方米；按原线及推定连接计算，带约数的区域需核对。")))
        (pl:range-session-loop)))))
(defun pl:range-work (kind / result)
  (if (not (and (boundp 'pl:*native-ui*) pl:*native-ui*))
    (alert "曲线几何面积需要配套的CountingTrees（数树）原生插件。请从CAD中的CountingTrees（数树）浮窗打开。")
    (progn
      (setq pl:*range-kind* kind)
      (setq result (vl-catch-all-apply 'pl:geometry-session-work nil))
      (vl-catch-all-apply 'pl:native-area-end nil) (setq pl:*range-kind* nil)
      (if (vl-catch-all-error-p result) (pl:rethrow result)))))

(defun pl:geometry-area-work () (pl:range-work -1))
(defun pl:shrub-work () (pl:range-work 1))
(defun pl:ground-work () (pl:range-work 2))

(defun pl:area-value (e / cached value)
  (if (and pl:*sync-busy* (setq cached (assoc e pl:*area-value-cache*))) (cdr cached)
    (progn
      (setq value (pl:uncached-area-value e))
      (if pl:*sync-busy* (setq pl:*area-value-cache* (cons (cons e value) pl:*area-value-cache*))) value)))
(defun pl:uncached-area-value (e / obj units result valid)
  (if (and (equal (pl:role e) "AREA") (setq units (pl:data-get e "UNITS")) (> units 0.0))
    (progn
      (if (and (boundp 'pl:*native-ui*) pl:*native-ui*)
        (setq result (pl:native-value (pl:native-area-value (cdr (assoc 5 (entget e))))))
        (progn
          (setq obj (vlax-ename->vla-object e)
            valid (or (= (cdr (assoc 0 (entget e))) "REGION")
              (and (= (cdr (assoc 0 (entget e))) "LWPOLYLINE") (= (vla-get-Closed obj) :vlax-true))))
          (if valid (setq result (vl-catch-all-apply 'vla-get-Area (list obj))))))
      (if (and (not (vl-catch-all-error-p result)) (numberp result) (> result 0.0))
        (/ result (* units units)) nil)) nil))

(defun pl:area-quantity-definition (e / p kind)
  (setq p (pl:data-get e "AREA_PLANT"))
  (if (not p)
    (progn
      ;; This is a table view of an unassigned area, never a saved plant definition.
      (setq kind (pl:data-get e "AREA_KIND")
        p (pl:empty-plant (strcat "GEOMETRY_" (cdr (assoc 5 (entget e))))))
      (setq p (pl:put 'name "未关联植物" (pl:put 'spec_no (pl:area-number e)
        (pl:put 'kind (if (member kind '(1 2)) kind 1) p))))))
  (pl:put 'quantity_unit "平方米" p))
(defun pl:quantity-data (e / p area)
  (cond
    ((setq p (pl:plant e)) (list p 1))
    ((and (equal (pl:role e) "AREA") (setq area (pl:area-value e)))
      (list (pl:area-quantity-definition e) area))
    (T nil)))

(defun pl:bind-area-plant (e p / previous result)
  (if (and p (equal (pl:role e) "AREA") (pl:writable e) (pl:area-value e))
    (progn
      (setq previous (pl:data-get e "AREA_PLANT"))
      (pl:data-put e "AREA_PLANT" p)
      (if (and (boundp 'pl:*native-ui*) pl:*native-ui*)
        (progn
          (setq result (vl-catch-all-apply 'pl:fill-area (list e)))
          (if (vl-catch-all-error-p result)
            (progn (pl:data-put e "AREA_PLANT" previous) (pl:rethrow result))))) T) nil))
(defun pl:area-from-selection (e)
  (cond ((equal (pl:role e) "AREA") e)
    ((member (pl:role e) '("AREA_LABEL" "AREA_LEADER" "AREA_ARROW" "AREA_FILL")) (pl:source e)) (T nil)))

(defun pl:bind-selected-areas (p / item e seen n skipped selection filter)
  (princ (strcat "\n选择计算边界或面积文字，关联为：" (pl:get 'name p) "；可多选，回车确认。"))
  (setq n 0 skipped 0 seen nil filter '((-3 ("PLANTCAD01")))
    selection (ssget "_I" filter))
  (if (not selection) (setq selection (ssget filter)))
  (sssetfirst nil nil)
  (foreach item (pl:ss-list selection)
    (if (and (setq e (pl:area-from-selection item)) (not (member e seen)))
      (progn
        (setq seen (cons e seen))
        (if (pl:bind-area-plant e p) (setq n (1+ n)) (setq skipped (1+ skipped))))))
  (if (> n 0) (progn (pl:sync-area-labels) (pl:ai-refresh-tables)))
  (princ (strcat "\n已关联 " (itoa n) " 个区域；锁定或无效区域跳过 " (itoa skipped) " 个。名称及面积标注和统计已更新。")))

(defun pl:area-bind-work (/ p)
  (if (not (pl:current)) (pl:library-work))
  (if (setq p (pl:current)) (pl:bind-selected-areas p)))

(defun pl:area-bind-label-work (/ pick p)
  (if (setq pick (entsel "\n选择已有灌木品种标注（植物图块、名称文字或引线）："))
    (if (setq p (pl:plant-from-picked-annotation (car pick)))
      (progn (pl:make-current-plant p) (pl:bind-selected-areas p)))))

(defun pl:all-areas (/ e result)
  (if (assoc 'areas pl:*entity-cache*) (cdr (assoc 'areas pl:*entity-cache*))
  (progn
  (foreach e (pl:ss-list (ssget "_X" '((0 . "LWPOLYLINE,REGION") (-3 ("PLANTCAD01")))))
    (if (equal (pl:role e) "AREA") (setq result (cons e result))))
  (reverse result))))

(defun pl:statistics-model (/ e result)
  (foreach e (append (pl:all-trees) (pl:all-areas))
    (if (not (equal 1 (cdr (assoc 67 (entget e))))) (setq result (cons e result))))
  (reverse result))

(defun pl:statistics-select (/ e result)
  (princ "\n选择或框选植物及种植范围：")
  (foreach e (pl:ss-list (ssget '((-3 ("PLANTCAD01")))))
    (if (or (pl:plant e) (equal (pl:role e) "AREA")) (setq result (cons e result))))
  (reverse result))

(defun pl:replace-work (/ p targets e n skipped)
  (if (setq p (pl:work-plant))
    (progn
      (princ (strcat "\n将所选植物替换为：" (pl:get 'name p) " / " (pl:get 'spec_no p)))
      (setq targets (pl:select-trees) n 0 skipped 0)
      (foreach e targets
        (if (pl:apply-plant e p) (setq n (1+ n)) (setq skipped (1+ skipped))))
      (pl:sync-labels)
      (princ (strcat "\n替换完成：" (itoa n) " 株；锁定或无效对象跳过 " (itoa skipped) " 株。")))))

(defun pl:label-preset (mode leader / opts)
  (setq opts (pl:db-get "LABEL_OPTIONS" '((mode . 0) (prefix . 0) (units . 0) (leader . 0))))
  (setq opts (pl:put 'mode mode (pl:put 'leader leader opts)))
  (if (not (pl:get 'height opts))
    (progn
      (if (not (pl:require-units)) (pl:fail "图纸单位未确认。"))
      (setq opts (pl:put 'height (pl:paper-height 2.5
        (pl:get 'scale (pl:db-get "PLOT_OPTIONS" '((scale . 100.0)))) (pl:units)) opts))))
  (pl:db-put "LABEL_OPTIONS" opts)
  (pl:label-work))

(defun pl:label-name-work () (pl:label-preset 0 0))
(defun pl:label-spec-work () (pl:label-preset 2 0))
(defun pl:label-number-work () (pl:label-preset 3 0))
(defun pl:label-leader-work () (pl:label-preset 0 1))

(defun pl:area-label-text (e / area repaired)
  (if (and (equal (pl:role e) "AREA") (setq area (pl:area-value e)))
    (progn (setq repaired (equal (pl:data-get e "AREA_REPAIRED") 1))
      (strcat (pl:mtext-safe (pl:area-title e)) "\\P" (if repaired "约 " "")
        (pl:area-text area) " 平方米" (if repaired "（补线推定）" ""))) nil))

(defun pl:create-area-label (e point / text opts units label height radius split columns)
  (if (and (setq text (pl:area-label-text e)) (not (pl:layer-issue "PL_标注_区域")))
    (progn
      (setq opts (pl:db-get "PLOT_OPTIONS" '((scale . 100.0) (paper_height . 2.5))) units (pl:data-get e "UNITS")
        height (pl:paper-height (pl:get 'paper_height opts) (pl:get 'scale opts) units)
        radius (pl:data-get e "AREA_LABEL_RADIUS"))
      (setq split (vl-string-search "\\P" text) columns (if split (max split (- (strlen text) split 2)) (strlen text)))
      (if (and (numberp radius) (> radius 0)) (setq height (min height (/ (* radius 3.6) (max 12 columns)))))
      (setq label (pl:make (list '(0 . "MTEXT") '(100 . "AcDbEntity") '(8 . "PL_标注_区域")
          '(62 . 256) '(100 . "AcDbMText") (cons 10 point) (cons 40 height)
          '(41 . 0.0) '(71 . 5) '(72 . 1) (cons 1 text) (cons 7 (getvar "TEXTSTYLE")))))
      (pl:mark label "AREA_LABEL" (cdr (assoc 5 (entget e))))
      (pl:data-put e "AREA_ANCHOR" point) (pl:data-put label "AREA_LABEL_TEXT" text) label)))
(defun pl:area-label-work () (pl:output-area-work))
(defun pl:legacy-area-label-work (/ pick e point)
  (pl:init-layers)
  (if (pl:layer-issue "PL_标注_区域") (pl:fail (pl:layer-issue "PL_标注_区域")))
  (while (setq pick (entsel "\n选择种植范围进行名称与面积标注，回车结束："))
    (setq e (car pick))
    (if (pl:area-label-text e)
      (if (setq point (getpoint "\n标注位置：")) (pl:create-area-label e (trans point 1 0)))
      (princ "\n请选择本插件生成的有效种植范围。"))))

(defun pl:sync-area-labels (/ label source text ed n height actual layer)
  (setq n 0)
  (foreach label (pl:all-labels)
    (if (and (equal (pl:role label) "AREA_LABEL") (pl:writable label)
             (setq source (pl:source label)) (setq text (pl:area-label-text source)))
      (progn
        (if (pl:data-get label "OUTPUT_OPTIONS")
          (setq text (pl:output-area-text source (pl:data-get label "OUTPUT_OPTIONS"))))
        (setq height (pl:area-annotation-height source (pl:data-get label "OUTPUT_OPTIONS"))
          layer (if (pl:data-get label "OUTPUT_OPTIONS") (pl:area-label-layer source) "PL_标注_区域"))
        (cond
          ((= (cdr (assoc 0 (entget label))) "MULTILEADER")
            (setq actual (pl:area-annotation-raw label))
            (if (or (not (equal text actual)) (not (equal layer (cdr (assoc 8 (entget label)))))
                    (not (equal height (pl:data-get label "OUTPUT_HEIGHT")))
                    (not (equal (pl:data-get label "OUTPUT_STYLE_VERSION") 2)))
              (progn
                (pl:write-native-area-label source (pl:data-get label "ANCHOR") '(0.0 0.0 0.0)
                  (pl:data-get label "OUTPUT_OPTIONS") label height)
                (setq n (1+ n)))))
          (T
            (setq ed (pl:set-dxf 40 height (pl:set-dxf 8 layer (pl:set-dxf 1 text (entget label)))))
            (if (not (equal ed (entget label)))
              (if (entmod ed) (progn (entupd label) (setq n (1+ n)))))))
        (if (not (equal text (pl:data-get label "AREA_LABEL_TEXT"))) (pl:data-put label "AREA_LABEL_TEXT" text)))))
  (princ (strcat "\n范围标注刷新 " (itoa n) " 项。")))

(defun pl:detail-work (/ pick e p quantity)
  (if (setq pick (entsel "\n选择植物或种植范围查看属性："))
    (progn
      (setq e (car pick) quantity (pl:quantity-data e))
      (if quantity
        (progn
          (setq p (car quantity))
          (alert (strcat "名称：" (pl:get 'name p) "\n规格：" (pl:get 'spec_no p)
            "\n" (pl:spec-text p) "\n数量：" (pl:num (cadr quantity)) " " (pl:get 'quantity_unit p))))
        (alert "对象没有本插件的有效植物或范围信息。")))))

(defun pl:layer-status-work (/ row issue text)
  (setq text "")
  (foreach row (pl:layers)
    (setq issue (pl:layer-issue (car row))
          text (strcat text (if issue issue (strcat (car row) "：可用")) "\n")))
  (alert (strcat "CountingTrees（数树） 图层状态\n\n" text "\n可在CAD图层管理器中调整。")))

(defun pl:count-all-work () (setq pl:*count-scope* "Model") (if (pl:count-work) (pl:output-table-create "PL_表格_苗木" "count" "苗木数量总表")))
(defun pl:count-selected-work () (setq pl:*count-scope* "Selected") (if (pl:count-work) (pl:output-table-create "PL_表格_苗木" "count" "所选范围苗木与面积表")))

(defun c:PLANTCADPICK () (pl:run 'pl:pick-current-work))
(defun c:PLANTCADREUSE () (pl:run 'pl:reuse-work))
(defun c:PLANTCADCIRCLE () (pl:run 'pl:circle-work))
(defun c:PLANTCADSIMPLE () (pl:run 'pl:simple-work))
(defun c:PLANTCADBLOCKPICK () (pl:run 'pl:block-pick-work))
(defun c:PLANTCADLINE () (pl:run 'pl:line-work))
(defun c:PLANTCADGRID () (pl:run 'pl:grid-work))
(defun c:PLANTCADAREA () (pl:run 'pl:geometry-area-work))
(defun c:PLANTCADAREABIND () (pl:run 'pl:area-bind-work))
(defun c:PLANTCADAREAFROMLABEL () (pl:run 'pl:area-bind-label-work))
(defun c:PLANTCADSHRUB () (pl:run 'pl:shrub-work))
(defun c:PLANTCADGROUND () (pl:run 'pl:ground-work))
(defun c:PLANTCADREPLACE () (pl:run 'pl:replace-work))
(defun c:PLANTCADLABELNAME () (pl:run 'pl:label-name-work))
(defun c:PLANTCADLABELSPEC () (pl:run 'pl:label-spec-work))
(defun c:PLANTCADLABELNUMBER () (pl:run 'pl:label-number-work))
(defun c:PLANTCADLABELLEADER () (pl:run 'pl:label-leader-work))
(defun c:PLANTCADLABELAREA () (pl:run 'pl:area-label-work))
(defun c:PLANTCADAREAADD () (pl:run 'pl:manual-area-work))
(defun c:PLANTCADDETAIL () (pl:run 'pl:detail-work))
(defun c:PLANTCADLAYERSTATUS () (pl:run 'pl:layer-status-work))
(defun c:PLANTCADCOUNTALL () (pl:run 'pl:count-all-work))
(defun c:PLANTCADCOUNTSELECTED () (pl:run 'pl:count-selected-work))

;;; 0.3.11: linked planting output. All metadata is persisted with the DWG.
(defun pl:fill-patterns () '("ANSI31" "ANSI32" "ANSI33" "ANSI34" "ANSI35" "ANSI36" "ANSI37" "ANSI38"))
(defun pl:fill-pattern-index (pattern / index found item)
  (setq index 0 found 0)
  (foreach item (pl:fill-patterns) (setq index (1+ index)) (if (equal item pattern) (setq found index))) found)
(defun pl:fill-pattern (p / pattern total c)
  (setq pattern (pl:get 'fill_pattern (pl:upgrade-plant p)))
  (if (member pattern (pl:fill-patterns)) pattern
    (progn
      (setq total 0)
      (foreach c (vl-string->list (pl:size-key p)) (setq total (+ total c)))
      (nth (rem total (length (pl:fill-patterns))) (pl:fill-patterns)))))
(defun pl:accept-fill-fields (/ size angle index)
  (setq size (pl:number-input (get_tile "fill_scale")) angle (pl:number-input (get_tile "fill_angle"))
    index (atoi (get_tile "fill_pattern")))
  (if (and size (> size 0) angle (>= angle 0) (< angle 360))
    (progn (setq pl:*fill-pattern* (if (= index 0) "" (nth (1- index) (pl:fill-patterns)))
      pl:*fill-scale* (/ size 100.0) pl:*fill-angle* angle) nil)
    "填充比例须大于0，角度范围为0至小于360度。"))
(defun pl:edit-name-choices (p / names species row index selected)
  (setq pl:*edit-choices* (list p) names (list (strcat "当前：" (pl:get 'name p))))
  (foreach species (pl:catalog)
    (setq row (pl:put 'species_id (pl:get 'id species)
      (pl:put 'name (pl:get 'name species) (pl:put 'kind (pl:species-kind (pl:get 'category species)) p))))
    (setq pl:*edit-choices* (append pl:*edit-choices* (list row)) names (append names (list (pl:get 'name species)))))
  (pl:popup "plant_choice" names) (set_tile "plant_choice" "0"))
(defun pl:edit-name-selected (value / p)
  (if (setq p (nth (atoi value) pl:*edit-choices*))
    (progn
      (setq pl:*edit* (pl:put 'species_id (pl:get 'species_id p) pl:*edit*))
      (set_tile "name" (pl:get 'name p))
      ;; Keep an explicitly chosen shrub-ball/flower-border/lawn role when changing species.
      (if (< (atoi (get_tile "kind")) 3) (set_tile "kind" (itoa (pl:get 'kind p)))))))
(defun pl:plant-label-layer (p)
  (cond ((= (pl:get 'kind p) 3) "PL_灌木球_标注") ((= (pl:get 'kind p) 4) "PL_花境_标注")
    ((member (pl:get 'kind p) '(2 5)) "PL_草地_标注") ((= (pl:get 'kind p) 1) "PL_灌木_标注")
    (T "PL_标注_树木")))
(defun pl:area-label-layer (e / p)
  (if (setq p (pl:data-get e "AREA_PLANT")) (pl:plant-label-layer p) "PL_标注_区域"))
(defun pl:fill-layer (p)
  (cond ((= (pl:get 'kind p) 4) "PL_花境_填充") ((member (pl:get 'kind p) '(2 5)) "PL_草地_填充")
    (T "PL_灌木_填充")))
(defun pl:fill-area (e / p signature state saved result)
  (if (and (boundp 'pl:*native-ui*) pl:*native-ui* (setq p (pl:data-get e "AREA_PLANT")) (pl:area-value e))
    (progn
      (setq p (pl:upgrade-plant p) signature (pl:native-value (pl:native-area-signature (cdr (assoc 5 (entget e)))))
        state (list (pl:fill-pattern p) (* (pl:get 'fill_scale p) (pl:data-get e "UNITS"))
          (* pi (/ (pl:get 'fill_angle p) 180.0)) (pl:fill-layer p) signature)
        saved (pl:data-get e "FILL_HANDLE"))
      (if (or (not (equal state (pl:data-get e "FILL_STATE"))) (not saved) (not (handent saved)))
        (progn
          (setq result (pl:native-value (pl:native-fill (cdr (assoc 5 (entget e))) (nth 0 state) (nth 1 state) (nth 2 state) (nth 3 state))))
          (if (or (/= (type result) 'STR) (= (substr result 1 6) "ERROR:"))
            (pl:fail (strcat "区域填充失败：" (if (= (type result) 'STR) result "没有返回图案"))))
          (pl:data-put e "FILL_STATE" state) (pl:data-put e "FILL_HANDLE" result))) T)))
(defun pl:selected-areas (/ selection item e result)
  (setq selection (ssget "_I" '((-3 ("PLANTCAD01")))))
  (if (not selection) (progn (princ "\n选择已算面积、面积文字或填充，可多选，回车确认：")
    (setq selection (ssget '((-3 ("PLANTCAD01")))))))
  (sssetfirst nil nil)
  (foreach item (pl:ss-list selection)
    (if (and (setq e (pl:area-from-selection item)) (not (member e result))) (setq result (append result (list e))))) result)
(defun pl:fill-work (/ areas p e n)
  (pl:init-layers)
  (setq areas (pl:selected-areas) n 0)
  (if areas
    (progn
      (if (not (pl:current)) (pl:library-work))
      (if (setq p (pl:current))
        (foreach e areas (if (pl:bind-area-plant e p) (setq n (1+ n)))))
      (princ (strcat "\n按当前植物种类填充 " (itoa n) " 个区域；可在规格中选用重复图案。")))))
(defun pl:placement-menu-work (/ choice)
  (initget "Point Ball Line Grid Fill Label Scan")
  (setq choice (getkword "\n开始布置 [单株(Point)/灌木球(Ball)/沿线(Line)/网格(Grid)/面积填充(Fill)/引线标注(Label)/扫描面积(Scan)] <Point>："))
  (cond ((= choice "Ball") (pl:ball-work)) ((= choice "Line") (pl:line-work)) ((= choice "Grid") (pl:grid-work))
    ((= choice "Fill") (pl:fill-work)) ((= choice "Label") (pl:output-area-work)) ((= choice "Scan") (pl:geometry-area-work)) (T (pl:insert-work))))
(defun pl:ball-work (/ p)
  (if (not (pl:current)) (pl:design-start))
  (if (setq p (pl:current))
    (progn
      (if (/= (pl:get 'kind p) 3)
        (progn
          (setq p (pl:put 'kind 3 (pl:put 'id (pl:new-id) (pl:put 'spec_no (pl:next-spec-number (pl:used-specs)) p))))
          (if (<= (pl:get 'crown p) 0) (setq p (pl:put 'crown 1.0 p)))
          (pl:save-def p) (pl:db-put "CURRENT" (pl:get 'id p))))
      (pl:insert-work))))

;;; Project edits update the existing specification; single-instance editing still creates variants.
(defun pl:edit-project-dialog (p / result)
  (setq pl:*project-edit* T)
  (setq result (vl-catch-all-apply 'pl:edit-dialog (list p)))
  (setq pl:*project-edit* nil)
  (if (vl-catch-all-error-p result) (pl:rethrow result) result))
(defun pl:save-project-spec (p / defs old history row kept e source)
  (setq defs (pl:defs) old (pl:by-id (pl:get 'id p)))
  (if (not old) (pl:save-def p)
    (progn
      (if (pl:plant-error p) (pl:fail (pl:plant-error p)))
      (if (pl:spec-error p (pl:used-specs)) (pl:fail (pl:spec-error p (pl:used-specs))))
      ;; Check all affected layers before committing the changed definition.
      (foreach e (append (pl:all-trees) (pl:all-areas))
        (setq source (if (equal (pl:role e) "AREA") (pl:data-get e "AREA_PLANT") (pl:plant e)))
        (if (and source (= (pl:get 'id source) (pl:get 'id p)))
          (progn
            (if (not (pl:writable e)) (pl:fail "该规格的图上对象图层已锁定，请解锁后再改项目规格。"))
            (if (pl:layer-issue (pl:plant-label-layer p)) (pl:fail (pl:layer-issue (pl:plant-label-layer p))))
            (if (pl:plant e)
              (progn
                (if (pl:insert-error p) (pl:fail (pl:insert-error p)))
                (if (pl:layer-issue (pl:tree-layer p)) (pl:fail (pl:layer-issue (pl:tree-layer p)))))
              (if (pl:layer-issue (pl:fill-layer p)) (pl:fail (pl:layer-issue (pl:fill-layer p))))))))
      (foreach e (pl:ss-list (ssget "_X" '((-3 ("PLANTCAD01")))))
        (if (and (not (pl:writable e))
          (or (equal (pl:role e) "TABLE")
            (and (setq source (pl:source e)) (setq source (pl:annotation-plant source))
              (= (pl:get 'id source) (pl:get 'id p)))))
          (pl:fail "该规格有关联标注、填充或表格图层锁定，请先解锁。")))
      (pl:db-put "PLANTS" (subst p old defs))
      (setq history (pl:db-get "SPEC_HISTORY" nil) kept nil)
      (foreach row history
        (if (/= (pl:get 'id row) (pl:get 'id p)) (setq kept (append kept (list row)))))
      (pl:db-put "SPEC_HISTORY" (append kept (list p))) (pl:remember-size p)
      (pl:built-blocks)
      (foreach e (pl:all-trees)
        (if (= (pl:get 'id (pl:plant e)) (pl:get 'id p))
          (if (not (pl:apply-plant e p)) (pl:fail "项目规格已修改，但图例更新失败；可用U撤销本次修改。"))))
      (foreach e (pl:all-areas)
        (if (and (setq row (pl:data-get e "AREA_PLANT")) (= (pl:get 'id row) (pl:get 'id p)))
          (progn (pl:data-put e "AREA_PLANT" p) (pl:fill-area e)))))) p)

;;; Output leader options are stored per annotation, preserving the selected layout on refresh.
(defun pl:output-area-text (e options / area title)
  (if (setq area (pl:area-value e))
    (progn
      (setq title (pl:mtext-safe (pl:area-title e)))
      (strcat title (if (= (pl:get 'layout options) 1) "  " "\\P")
        (if (equal (pl:data-get e "AREA_REPAIRED") 1) "约 " "")
        (pl:area-text area) " 平方米" (if (equal (pl:data-get e "AREA_REPAIRED") 1) "（补线推定）" "")))))
(defun pl:area-output-options (/ id saved status)
  (setq saved (pl:db-get "AREA_OUTPUT_OPTIONS" '((layout . 0) (fill . 1) (bind . 0)))
    id (pl:dialog "pl_area_output") pl:*area-output-result* nil)
  (if id
    (progn
      (pl:popup "area_layout" '("上行植物、下行面积（引线横线居中）" "植物在前、面积在后（同在横线上方）"))
      (set_tile "area_layout" (itoa (pl:get 'layout saved)))
      (set_tile "area_fill" (itoa (pl:get 'fill saved))) (set_tile "area_bind" (itoa (pl:get 'bind saved)))
      (action_tile "accept" "(setq pl:*area-output-result* (list (cons 'layout (atoi (get_tile \"area_layout\"))) (cons 'fill (atoi (get_tile \"area_fill\"))) (cons 'bind (atoi (get_tile \"area_bind\"))))) (done_dialog 1)")
      (action_tile "cancel" "(done_dialog 0)")
      (setq status (start_dialog)) (unload_dialog id)
      (if (= status 1) (progn (pl:db-put "AREA_OUTPUT_OPTIONS" pl:*area-output-result*) pl:*area-output-result*) nil))))
(defun pl:area-output-linked (area / result e)
  (foreach e (pl:ss-list (ssget "_X" '((-3 ("PLANTCAD01")))))
    (if (and (member (pl:role e) '("AREA_LABEL" "AREA_LEADER" "AREA_ARROW")) (equal (pl:source e) area))
      (setq result (cons e result)))) result)
(defun pl:output-leader-shape (label / area point anchor height width elbow end line arrow layer direction side a b c old text split columns)
  (setq area (pl:source label) point (cdr (assoc 10 (entget label))) anchor (pl:data-get label "ANCHOR")
    height (cdr (assoc 40 (entget label))) layer (pl:area-label-layer area)
    text (cdr (assoc 1 (entget label))) split (vl-string-search "\\P" text)
    columns (if split (max split (- (strlen text) split 2)) (strlen text))
    width (* height 0.55 (max 12 columns)))
  (setq elbow (list (- (car point) (* 2 height)) (cadr point) (caddr point))
    end (list (+ (car point) width) (cadr point) (caddr point)))
  (foreach old (pl:area-output-linked area)
    (if (and (member (pl:role old) '("AREA_LEADER" "AREA_ARROW")) (pl:writable old)) (entdel old)))
  (setq line (pl:make (list '(0 . "LWPOLYLINE") '(100 . "AcDbEntity") (cons 8 layer) '(62 . 256)
    '(100 . "AcDbPolyline") '(90 . 3) '(70 . 0) (cons 38 (caddr point))
    (cons 10 (list (car anchor) (cadr anchor))) (cons 10 (list (car elbow) (cadr elbow))) (cons 10 (list (car end) (cadr end))))))
  (pl:mark line "AREA_LEADER" (cdr (assoc 5 (entget area))))
  (setq direction (angle anchor elbow) side (* height 0.3)
    a anchor b (polar anchor (+ direction 0.25) side) c (polar anchor (- direction 0.25) side))
  (setq arrow (pl:make (list '(0 . "SOLID") (cons 8 layer) '(62 . 256) (cons 10 a) (cons 11 b) (cons 12 c) (cons 13 c))))
  (pl:mark arrow "AREA_ARROW" (cdr (assoc 5 (entget area))))
  (pl:data-put label "LEADER_POSITION" point)
  (pl:data-put label "LEADER_STATE" (list point text height layer)))
(defun pl:write-native-area-label (e anchor point options existing height / result label units plot args)
  (if (not height)
    (progn
      (setq units (pl:data-get e "UNITS") plot (pl:db-get "PLOT_OPTIONS" '((scale . 100.0) (paper_height . 2.5))))
      (setq height (pl:paper-height (pl:get 'paper_height plot)
        (if (= (cdr (assoc 67 (entget e))) 1) 1.0 (pl:get 'scale plot)) units))))
  (setq args (list
    (if existing (cdr (assoc 5 (entget existing))) "") (cdr (assoc 5 (entget e)))
    anchor point (pl:output-area-text e options) height (pl:area-label-layer e) (pl:get 'layout options)))
  (if (pl:get 'elbow options) (setq args (append args (list (pl:get 'elbow options)))))
  (setq result (pl:native-value (apply 'pl:native-area-leader args)))
  (if (or (/= (type result) 'STR) (= (substr result 1 6) "ERROR:"))
    (pl:fail (strcat "整体引线生成失败：" (if (= (type result) 'STR) result "没有返回标注"))))
  (setq label (handent result))
  (pl:data-put label "OUTPUT_OPTIONS" options) (pl:data-put label "ANCHOR" anchor)
  (pl:data-put label "OUTPUT_STYLE_VERSION" 2)
  (pl:data-put label "OUTPUT_HEIGHT" height) (pl:data-put label "AREA_LABEL_TEXT" (pl:output-area-text e options)) label)
(defun pl:area-annotation-height (e output / plot units height radius text split columns)
  (setq plot (pl:db-get "PLOT_OPTIONS" '((scale . 100.0) (paper_height . 2.5))) units (pl:data-get e "UNITS")
    height (pl:paper-height (pl:get 'paper_height plot) (if (= (cdr (assoc 67 (entget e))) 1) 1.0 (pl:get 'scale plot)) units))
  (if (not output)
    (progn (setq radius (pl:data-get e "AREA_LABEL_RADIUS") text (pl:area-label-text e)
      split (vl-string-search "\\P" text) columns (if split (max split (- (strlen text) split 2)) (strlen text)))
      (if (and (numberp radius) (> radius 0)) (setq height (min height (/ (* radius 3.6) (max 12 columns))))))) height)
(defun pl:output-area-label (e anchor point options / old item label)
  (if (and (boundp 'pl:*native-ui*) pl:*native-ui*)
    (progn
      (setq old (pl:area-output-linked e))
      (foreach item old (if (not (pl:writable item)) (pl:fail "原面积标注图层已锁定，请先解锁。")))
      (setq label (pl:write-native-area-label e anchor point options nil nil))
      (foreach item old (entdel item)) label)
    (pl:legacy-output-area-label e anchor point options)))
(defun pl:legacy-output-area-label (e anchor point options / height units plot label old item layer text)
  (setq layer (pl:area-label-layer e) old (pl:area-output-linked e))
  (if (pl:layer-issue layer) (pl:fail (pl:layer-issue layer)))
  (foreach item old (if (not (pl:writable item)) (pl:fail "原面积标注图层已锁定，请先解锁。")))
  (setq units (pl:data-get e "UNITS") plot (pl:db-get "PLOT_OPTIONS" '((scale . 100.0) (paper_height . 2.5)))
    height (pl:paper-height (pl:get 'paper_height plot)
      (if (= (cdr (assoc 67 (entget e))) 1) 1.0 (pl:get 'scale plot)) units)
    text (pl:output-area-text e options))
  (setq label (pl:make (list '(0 . "MTEXT") '(100 . "AcDbEntity") (cons 8 layer) '(62 . 256)
    '(100 . "AcDbMText") (cons 10 point) (cons 40 height) '(41 . 0.0)
    (cons 71 (if (= (pl:get 'layout options) 1) 7 4)) '(72 . 1) (cons 1 text) (cons 7 (getvar "TEXTSTYLE")))))
  (pl:mark label "AREA_LABEL" (cdr (assoc 5 (entget e))))
  (pl:data-put label "OUTPUT_OPTIONS" options) (pl:data-put label "ANCHOR" anchor)
  (foreach item old (entdel item))
  (pl:output-leader-shape label) label)
(defun pl:try-fill-area (e / result previous reason)
  (setq previous pl:*failure* pl:*failure* nil result (vl-catch-all-apply 'pl:fill-area (list e)))
  (if (vl-catch-all-error-p result)
    (progn
      (setq reason (if pl:*failure* pl:*failure* (vl-catch-all-error-message result)))
      (princ (strcat "\n区域 " (pl:area-number e) " 的填充未完成：" reason "；已生成的引线和文字保留。"))))
  (setq pl:*failure* previous)
  (not (vl-catch-all-error-p result)))
(defun pl:upgrade-area-leaders (/ label source options old safe item n)
  (setq n 0)
  (if (and (boundp 'pl:*native-ui*) pl:*native-ui*)
    (foreach label (pl:all-labels)
      (if (and (= (cdr (assoc 0 (entget label))) "MTEXT") (equal (pl:role label) "AREA_LABEL")
        (setq options (pl:data-get label "OUTPUT_OPTIONS")) (setq source (pl:source label)) (entget source)
        (pl:data-get label "ANCHOR"))
        (progn
          (setq old (pl:area-output-linked source) safe T)
          (foreach item old (if (not (pl:writable item)) (setq safe nil)))
          (if safe
            (progn
              (pl:write-native-area-label source (pl:data-get label "ANCHOR")
                (cdr (assoc 10 (entget label))) options nil (cdr (assoc 40 (entget label))))
              (foreach item old (entdel item)) (setq n (1+ n)))))))) n)
(defun pl:area-label-name (e name / matches p kind)
  (setq name (pl:trim name))
  (if (/= name "")
    (progn
      (setq matches (pl:label-plant-matches (list name) (pl:defs)))
      (cond
        ((= (length matches) 1) (setq p (car matches)))
        ((> (length matches) 1) (princ "\n此名称有多个规格，请输入唯一的规格编号，或从项目规格选择。"))
        (T
          (setq kind (pl:data-get e "AREA_KIND") p (pl:empty-plant (pl:new-id)))
          (setq p (pl:put 'name name (pl:put 'kind (if (member kind '(1 2 4 5)) kind 1)
            (pl:put 'quantity_unit "平方米" (pl:put 'spec_no (pl:next-spec-number (pl:used-specs)) p)))))
          (pl:save-def p)))
      (if p (pl:data-put e "AREA_PLANT" p)))) p)
(defun pl:area-annotation-raw (label)
  (if (= (cdr (assoc 0 (entget label))) "MULTILEADER")
    (pl:native-value (pl:native-leader-text (cdr (assoc 5 (entget label)))) ) (cdr (assoc 1 (entget label)))))
(defun pl:area-label-name-edits (/ edits label area raw baseline expected name pair matches)
  (foreach label (pl:all-labels)
    (if (and (equal (pl:role label) "AREA_LABEL") (setq area (pl:source label)) (entget area)
      (setq raw (pl:area-annotation-raw label)))
      (progn
        (setq baseline (pl:data-get label "AREA_LABEL_TEXT")
          expected (if (pl:data-get label "OUTPUT_OPTIONS") (pl:output-area-text area (pl:data-get label "OUTPUT_OPTIONS")) (pl:area-label-text area)))
        (if (not (equal raw (if baseline baseline expected)))
          (progn
            (setq name (pl:native-value (pl:native-area-label-name (cdr (assoc 5 (entget label))))))
            (if (and (= (type name) 'STR) (= (substr name 1 6) "ERROR:")) (pl:fail name))
            (if (and name (/= name "") (not (equal (pl:normal-name name) (pl:normal-name (pl:area-title area)))))
              (progn
                (if (or (not (pl:writable area)) (not (pl:writable label))) (pl:fail "改名区域或标注图层锁定，请先解锁。"))
                (setq matches (pl:label-plant-matches (list name) (pl:defs)) pair (assoc area edits))
                (if (> (length matches) 1) (pl:fail "改后的灌木名称对应多个规格，请输入唯一规格编号，或在项目规格明确选择后关联。"))
                (if (and pair (not (equal name (cadr pair)))) (pl:fail "同一区域的多条标注改成了不同植物，请先统一名称。"))
                (if (not pair) (setq edits (append edits (list (list area name)))))))))))) edits)
(defun pl:import-area-label-edits (/ edits pair count)
  ;; Direct CAD text edits are imported on explicit sync/statistics, never from reactors.
  ;; A project/specification change takes precedence over an old label's displayed text.
  (if (and (boundp 'pl:*native-ui*) pl:*native-ui* (not pl:*drawing-changed*))
    (progn
      (setq edits (pl:area-label-name-edits) count 0)
      (foreach pair edits
        (if (pl:area-label-name (car pair) (cadr pair)) (setq count (1+ count))
          (pl:fail "灌木名称未能关联，请在项目规格中选定后重新关联。")))
      (if (> count 0) (princ (strcat "\n已识别 " (itoa count) " 个直接修改的灌木名称，面积继续按边界计算。"))) count)))
(defun pl:area-label-geometry (e anchor / elbow tail valid)
  (if (setq elbow (getpoint (trans anchor 0 1)
    (strcat "\n" (pl:area-number e) " 第一点：指定引线折点（回车跳过）：")))
    (progn
      (setq elbow (trans elbow 1 0))
      (while (and (not valid) (setq tail (getpoint (trans elbow 0 1)
        "\n第二点：指定横线尾端，向左或向右（与折点保持水平；回车跳过）：")))
        (setq tail (trans tail 1 0))
        (if (< (abs (- (car elbow) (car tail))) 1.0e-8)
          (princ "\n横线尾端须在折点左侧或右侧，请重新点选。")
          (setq valid T tail (list (car tail) (cadr elbow) (caddr elbow)))))
      (if valid (list elbow tail)))))
(defun pl:area-species-filter (/ p)
  (setq pl:*area-species-visible* (pl:project-filter (pl:defs) -1 (get_tile "area_query"))
    pl:*area-species-picked* nil)
  (start_list "area_columns") (add_list (pl:project-columns)) (end_list)
  (start_list "area_plants")
  (foreach p pl:*area-species-visible* (add_list (pl:project-list-row p))) (end_list))
(defun pl:area-species-row (value)
  (if (setq pl:*area-species-picked* (nth (atoi value) pl:*area-species-visible*))
    (set_tile "area_name" (pl:get 'name pl:*area-species-picked*))))
(defun pl:area-species-accept (/ name p matches)
  (setq name (pl:trim (get_tile "area_name")) p pl:*area-species-picked*)
  (if (and p (not (equal (pl:normal-name name) (pl:normal-name (pl:get 'name p))))) (setq p nil))
  (if (not p) (setq matches (pl:label-plant-matches (list name) (pl:defs))))
  (cond
    ((= name "") (alert "请选择项目品种，或输入植物名称。"))
    ((and (not p) (> (length matches) 1)) (alert "同名植物有多个规格，请在列表中选择具体规格，或输入唯一的规格编号。"))
    (T
      (if (and (not p) matches) (setq p (car matches)))
      (setq pl:*area-species-result* (if p (list "plant" p) (list "name" name))) (done_dialog 1))))
(defun pl:area-output-plant (e initial / id status quit p index row result)
  (setq p initial quit nil result nil)
  (while (not quit)
    (setq id (pl:dialog "pl_area_species") pl:*area-species-result* nil)
    (if (not id) (setq quit T)
      (progn
        (set_tile "area_query" "") (set_tile "area_name" (if p (pl:get 'name p) ""))
        (pl:area-species-filter)
        (setq pl:*area-species-picked* p index 0)
        (foreach row pl:*area-species-visible*
          (if (and p (equal (pl:get 'id row) (pl:get 'id p)))
            (progn (set_tile "area_plants" (itoa index)) (setq pl:*area-species-picked* row)))
          (setq index (1+ index)))
        (action_tile "area_query" "(pl:area-species-filter)")
        (action_tile "area_search" "(pl:area-species-filter)")
        (action_tile "area_plants" "(pl:area-species-row $value)")
        (action_tile "area_add" "(done_dialog 2)")
        (action_tile "accept" "(pl:area-species-accept)") (action_tile "cancel" "(done_dialog 0)")
        (setq status (start_dialog)) (unload_dialog id)
        (cond ((= status 2) (pl:add-from-catalog))
          ((= status 1) (setq result pl:*area-species-result* quit T)) (T (setq quit T))))))
  (if result (if (= (car result) "plant") (cadr result) (pl:area-label-name e (cadr result)))))
(defun pl:output-area-work (/ areas options p e anchor geometry chosen)
  (pl:import-area-label-edits)
  (pl:init-layers)
  (setq areas (pl:selected-areas))
  (if (and areas (setq options (pl:area-output-options)))
    (progn
      (setq p (pl:current))
      (foreach e areas
        (setq anchor (pl:data-get e "AREA_ANCHOR"))
        (if (not anchor)
          (if (setq anchor (getpoint "\n点选该区域内的引线起点：")) (setq anchor (trans anchor 1 0))))
        (if (and anchor (setq geometry (pl:area-label-geometry e anchor))
          (setq chosen (pl:area-output-plant e
            (if (or (= (pl:get 'bind options) 1) (not (pl:data-get e "AREA_PLANT"))) p (pl:data-get e "AREA_PLANT")))))
          (progn
            (setq p chosen) (pl:data-put e "AREA_PLANT" p) (pl:db-put "CURRENT" (pl:get 'id p))
            (pl:output-area-label e anchor (cadr geometry) (pl:put 'elbow (car geometry) options))
            (if (= (pl:get 'fill options) 1) (pl:try-fill-area e))))))))

;;; All three schedule types are native, linked ACAD_TABLE entities with block legends.
(defun pl:output-table-headers () '("编号" "图例" "植物名称" "类别" "胸径 cm" "地径 cm" "高度 cm" "冠幅 cm" "数量/面积" "单位"))
(defun pl:table-display-row (row)
  (append (list (car row) (nth 9 row)) (reverse (cdr (reverse (cdr row))))))
(defun pl:table-category (p)
  (cond ((= (pl:get 'kind p) 0) "trees") ((= (pl:get 'kind p) 3) "balls") (T "cover")))
(defun pl:table-category-title (group)
  (cond ((equal group "trees") "乔木") ((equal group "balls") "灌木球") (T "灌木地被（含花境、草坪）")))
(defun pl:table-species-key (p / id)
  (setq id (pl:get 'species_id p))
  (if (and id (/= id "")) (strcat "ID:" id) (strcat "NAME:" (pl:normal-name (pl:get 'name p)))))
(defun pl:table-record-matches (p scope)
  (and (or (not (pl:get 'category scope)) (equal (pl:get 'category scope) (pl:table-category p)))
    (or (not (pl:get 'species_key scope)) (equal (pl:get 'species_key scope) (pl:table-species-key p))
      (and (= (substr (pl:get 'species_key scope) 1 5) "NAME:")
        (or (not (pl:get 'species_id p)) (= (pl:get 'species_id p) ""))
        (member (pl:get 'id p) (pl:get 'species_specs scope))))))
(defun pl:table-species-scope (p records scope / key ids row id)
  (setq key (pl:table-species-key p))
  (foreach row records
    (if (and (equal key (pl:table-species-key (car row))) (setq id (pl:get 'id (car row))) (not (member id ids)))
      (setq ids (append ids (list id)))))
  (pl:put 'species_specs ids (pl:put 'species_key key scope)))
(defun pl:output-table-objects (scope / result h e)
  (if (= (pl:get 'scope scope) "model") (pl:statistics-model)
    (progn
      (foreach h (pl:get 'handles scope)
        (if (and (setq e (handent h)) (pl:quantity-data e)) (setq result (append result (list e))))) result)))
(defun pl:output-table-records (kind scope / result row p counts records)
  (if (and (boundp 'pl:*split-kind*) (equal kind pl:*split-kind*))
    (setq records pl:*split-records*)
    (if (= kind "count")
      (progn (setq counts (pl:output-counts scope))
        (foreach row counts (setq records (append records (list (list (cadr row) (caddr row)))))))
      (foreach p (pl:ai-visible-defs)
        (setq records (append records (list (list p nil)))))))
  (foreach row records (if (pl:table-record-matches (car row) scope) (setq result (append result (list row))))) (pl:sort-plant-records result))
(defun pl:output-table-cells (record / p quantity legend)
  (setq p (car record) quantity (cadr record))
  (setq legend (if (or (= (pl:get 'quantity_unit p) "平方米") (and (null quantity) (pl:area-kind-p (pl:get 'kind p))))
    (strcat "HATCH:" (pl:fill-pattern p)) (pl:block-name p)))
  (list (pl:get 'spec_no p) (pl:get 'name p) (pl:kind-name (pl:get 'kind p))
    (pl:dimension-text 'dbh p) (pl:dimension-text 'caliper p) (pl:dimension-text 'height p) (pl:dimension-text 'crown p)
    (if quantity (pl:quantity-text p quantity) "") (pl:get 'quantity_unit p) legend))
(defun pl:table-legend-layout (p / plot scale height values diameter spec)
  (setq plot (pl:db-get "PLOT_OPTIONS" '((scale . 100.0) (paper_height . 2.5) (show_number . 0)))
    scale (pl:block-scale p 1.0))
  (if (<= scale 0) (setq scale 1.0))
  (setq height (/ (pl:paper-height (pl:get 'paper_height plot) (pl:get 'scale plot) 1.0) scale)
    values (pl:symbol-attribute "PL_DIAMETER" p '(0.0 0.0 0.0) height plot)
    diameter (if (caddr values) "" (car values))
    values (pl:symbol-attribute "PL_SPEC" p '(0.0 0.0 0.0) height plot)
    spec (if (caddr values) "" (car values)))
  (list height (pl:get 'kind p) (pl:get 'name p) diameter spec))
(defun pl:output-table-write (e point layer kind title height scope / records cells snapshot layouts record result)
  (pl:built-blocks)
  (setq records (pl:output-table-records kind scope))
  (foreach record records
    (setq cells (append cells (list (pl:table-display-row (pl:output-table-cells record))))
      snapshot (append snapshot (list (list (pl:get 'id (car record)) (pl:output-table-cells record))))
      layouts (append layouts (list (pl:table-legend-layout (car record))))))
  (setq result (pl:native-value (pl:native-table-write (if e (cdr (assoc 5 (entget e))) "") point layer title height (pl:output-table-headers) cells layouts)))
  (if (or (/= (type result) 'STR) (= (substr result 1 6) "ERROR:"))
    (pl:fail (strcat "关联表更新失败：" (if (= (type result) 'STR) result "没有返回表格"))))
  (setq e (handent result))
  (pl:data-put e "TABLE_KIND" kind) (pl:data-put e "TABLE_TITLE" title) (pl:data-put e "TABLE_HEIGHT" height)
  (pl:data-put e "TABLE_SCOPE" scope) (pl:data-put e "TABLE_ROWS" snapshot)
  (pl:data-put e "TABLE_LEGENDS" layouts) (pl:data-put e "TABLE_FORMAT" 4) e)
(defun pl:output-table-create (layer kind title / height point plot scope)
  (pl:init-layers)
  (if (not (and (boundp 'pl:*native-ui*) pl:*native-ui*)) (pl:fail "带图例的关联表需要配套原生插件，请从CountingTrees（数树）浮窗使用。"))
  (if (pl:require-units)
    (progn
      (setq plot (pl:db-get "PLOT_OPTIONS" '((scale . 100.0) (paper_height . 2.5)))
        height (pl:paper-height (pl:get 'paper_height plot) (if (and (= (getvar "TILEMODE") 0) (= (getvar "CVPORT") 1)) 1.0 (pl:get 'scale plot)) (pl:units)))
      (if (setq point (getpoint (strcat "\n" title "插入点（原生关联表，带图例与编号）：")))
        (progn
          (setq scope (if (= kind "count") (pl:db-get "LAST_COUNT_SCOPE" '((scope . "model"))) '((scope . "model"))))
          (pl:output-table-write nil (trans point 1 0) layer kind title height scope)
          (princ "\n已生成关联表。项目规格修改自动关联；直接编辑表格后，请执行“更新关联标注”同步。"))))))
(defun pl:output-table-refresh (e / kind scope records snapshot layouts record title)
  (setq kind (pl:data-get e "TABLE_KIND") scope (pl:data-get e "TABLE_SCOPE") records (pl:output-table-records kind scope))
  (foreach record records (setq snapshot (append snapshot (list (list (pl:get 'id (car record)) (pl:output-table-cells record))))
    layouts (append layouts (list (pl:table-legend-layout (car record))))))
  (setq title (pl:data-get e "TABLE_TITLE"))
  (if (and (equal kind "count") (equal (pl:get 'scope scope) "model") (not (pl:get 'category scope)) (not (pl:get 'species_key scope)))
    (setq title "苗木数量总表"))
  (if (and (pl:get 'species_key scope) records) (setq title (strcat (pl:get 'name (caar records)) " · " (pl:table-kind-title kind))))
  (if (or (not (equal snapshot (pl:data-get e "TABLE_ROWS"))) (not (equal (pl:data-get e "TABLE_FORMAT") 4))
    (not (equal layouts (pl:data-get e "TABLE_LEGENDS")))
    (not (equal title (pl:data-get e "TABLE_TITLE"))))
    (pl:output-table-write e '(0.0 0.0 0.0) (cdr (assoc 8 (entget e))) kind title (pl:data-get e "TABLE_HEIGHT") scope)))
(defun pl:table-kind-title (kind)
  (cond ((equal kind "count") "苗木数量总表") ((equal kind "list") "植物名录表") (T "植物规格表")))
(defun pl:table-split-groups (records mode scope / groups category row p key seen filtered)
  (if (equal mode "category")
    (foreach category '("trees" "balls" "cover")
      (setq filtered nil)
      (foreach row records (if (equal (pl:table-category (car row)) category) (setq filtered T)))
      (if filtered (setq groups (append groups (list (list (pl:table-category-title category) (pl:put 'category category scope)))))))
    (foreach row records
      (setq p (car row) key (pl:table-species-key p))
      (if (not (member key seen))
        (setq seen (cons key seen) groups (append groups (list (list (pl:get 'name p) (pl:table-species-scope p records scope)))))))) groups)
(defun pl:output-tables-split (source layer kind scope mode / groups point height plot group table result records pl:*split-kind* pl:*split-records*)
  (pl:init-layers)
  (if (not (and (boundp 'pl:*native-ui*) pl:*native-ui*)) (pl:fail "分类关联表需要配套原生插件。"))
  (if (pl:require-units)
    (progn
      (setq records (pl:output-table-records kind scope) groups (pl:table-split-groups records mode scope)
        pl:*split-kind* kind pl:*split-records* records)
      (if (not groups) (princ "\n此范围没有可拆分的植物记录。")
        (if (setq point (getpoint "\n指定第一张表的左上角，各表自动向下排列（回车取消）："))
          (progn
            (setq point (trans point 1 0) height (if source (pl:data-get source "TABLE_HEIGHT")))
            (if (not height)
              (progn (setq plot (pl:db-get "PLOT_OPTIONS" '((scale . 100.0) (paper_height . 2.5))))
                (setq height (pl:paper-height (pl:get 'paper_height plot)
                  (if (and (= (getvar "TILEMODE") 0) (= (getvar "CVPORT") 1)) 1.0 (pl:get 'scale plot)) (pl:units)))))
            (foreach group groups
              (setq table (pl:output-table-write nil point layer kind (strcat (car group) " · " (pl:table-kind-title kind)) height (cadr group))
                result (append result (list table))
                point (list (car point) (- (cadr point) (* height (+ 6.0 (* 2.8 (max 3 (+ 2 (length (pl:output-table-records kind (cadr group))))))))) (caddr point))))
            (princ (strcat "\n已生成 " (itoa (length result)) " 张关联表，空类别跳过。原总表保留，可移动各表或自行删除总表；规格修改仍会同步。"))))))) result)
(defun pl:table-count-split-work (mode)
  (if (pl:count-work) (pl:output-tables-split nil "PL_表格_苗木" "count" (pl:db-get "LAST_COUNT_SCOPE" '((scope . "model"))) mode)))
(defun pl:table-existing-split-work (/ pick table kind mode)
  (if (setq pick (entsel "\n选择CountingTrees（数树）生成的数量表、名录表或规格表（原表保留）："))
    (progn
      (setq table (car pick) kind (pl:data-get table "TABLE_KIND"))
      (if (not (and (= (cdr (assoc 0 (entget table))) "ACAD_TABLE") (member kind '("count" "list" "specs"))))
        (pl:fail "请选择带植物关联记录的CountingTrees（数树）表格；普通表请先重新统计生成。"))
      (pl:import-area-label-edits)
      (initget "Category Species")
      (setq mode (getkword "\n拆分方式 [三类(Category)/按品种(Species)] <Category>："))
      (pl:output-tables-split table (cdr (assoc 8 (entget table))) kind (pl:data-get table "TABLE_SCOPE")
        (if (equal mode "Species") "species" "category")))))
(defun c:PLANTCADTABLEGROUPS () (pl:run '(lambda () (pl:table-count-split-work "category"))))
(defun c:PLANTCADTABLESPECIES () (pl:run '(lambda () (pl:table-count-split-work "species"))))
(defun c:PLANTCADTABLESPLIT () (pl:run 'pl:table-existing-split-work))
(defun pl:table-edited-plant (p before after / index key value message)
  (setq index 0 message nil)
  (foreach key '(spec_no name kind dbh caliper height crown)
    (if (not (equal (nth index before) (nth index after)))
      (cond
        ((member key '(spec_no name)) (setq p (pl:put key (pl:trim (nth index after)) p)))
        ((= key 'kind) (setq message "类别请在项目规格中修改；表格支持修改名称、编号及尺寸。"))
        (T (setq value (pl:dimension-input key (nth index after) (pl:get 'kind p)))
          (if value (setq p (pl:put key value p)) (setq message "表格规格须填写cm数值、留空或——。")))))
    (setq index (1+ index)))
  (if (not message) (setq message (pl:plant-error p)))
  (if message (pl:fail message) p))
(defun pl:import-table-edits (/ table saved actual before after row index p changed edits pair)
  (foreach table (pl:ss-list (ssget "_X" '((0 . "ACAD_TABLE") (-3 ("PLANTCAD01")))))
    (if (and (pl:data-get table "TABLE_KIND") (setq saved (pl:data-get table "TABLE_ROWS")))
      (progn
        (setq actual (pl:native-table-read (cdr (assoc 5 (entget table)))))
        (if (and (listp actual) (equal (car actual) "TABLE_ROWS"))
          (progn
            (setq index 0)
            (foreach row saved
              (setq before (cadr row) after (nth index (cdr actual)) index (1+ index))
              (if (and after (setq p (pl:by-id (car row))))
                (progn
                  (setq changed (pl:table-edited-plant p before after))
                  (if (not (equal changed p))
                    (progn
                      (if (and (setq pair (assoc (car row) edits)) (not (equal (cadr pair) changed)))
                        (pl:fail "多个表格对同一规格有不同修改，请保留一处修改后再同步。"))
                      (if (not pair) (setq edits (append edits (list (list (car row) changed))))))))))
            ;; Refresh also restores edits to computed columns and deleted rows.
            (if (not (equal (mapcar '(lambda (x) (reverse (cdr (reverse (cadr x))))) saved) (cdr actual)))
              (pl:data-put table "TABLE_ROWS" nil)))))))
  (foreach pair edits (pl:save-project-spec (cadr pair))))
(defun pl:sync-drawing (/ e source role)
  (if (not pl:*sync-busy*)
    (progn
      (setq pl:*sync-busy* T pl:*entity-cache* nil pl:*link-cache* nil pl:*area-value-cache* nil pl:*count-cache* nil)
      (setq pl:*sync-result* (vl-catch-all-apply 'pl:sync-drawing-work nil))
      (setq pl:*sync-busy* nil pl:*entity-cache* nil pl:*link-cache* nil pl:*area-value-cache* nil pl:*count-cache* nil)
      (if (vl-catch-all-error-p pl:*sync-result*) (pl:rethrow pl:*sync-result*))))
  T)
(defun pl:sync-drawing-work (/ e source role point state)
  (pl:import-area-label-edits)
  (pl:upgrade-area-leaders)
  (if (and (boundp 'pl:*native-ui*) pl:*native-ui*) (pl:import-table-edits))
  (foreach e (pl:ss-list (ssget "_X" '((-3 ("PLANTCAD01")))))
    (setq role (pl:role e))
    (if (and (member role '("AREA_LABEL" "AREA_LEADER" "AREA_ARROW" "AREA_FILL" "FILL_EDGE" "LABEL" "LEADER"))
      (not (pl:source e)) (pl:writable e)) (entdel e)))
  (pl:cache-entities)
  (foreach e (pl:all-areas)
    (if (and (pl:data-get e "FILL_HANDLE") (pl:writable e)) (pl:try-fill-area e)))
  (pl:sync-labels)
  (foreach e (pl:all-labels)
    (if (and (equal (pl:role e) "AREA_LABEL") (= (cdr (assoc 0 (entget e))) "MTEXT") (pl:data-get e "OUTPUT_OPTIONS") (pl:writable e))
      (progn
        (setq point (cdr (assoc 10 (entget e)))
          state (list point (cdr (assoc 1 (entget e))) (cdr (assoc 40 (entget e))) (pl:area-label-layer (pl:source e))))
        (if (not (equal state (pl:data-get e "LEADER_STATE"))) (pl:output-leader-shape e)))))
  (pl:ai-refresh-tables))
(defun pl:sync-native () (pl:run 'pl:sync-drawing))
(vl-acad-defun 'pl:sync-native)
(defun c:PLANTCADFILL () (pl:run 'pl:fill-work))
(defun c:PLANTCADBALL () (pl:run 'pl:ball-work))
(defun c:PLANTCADARRANGE () (pl:run 'pl:placement-menu-work))

;;; A read-only dialog does not require redrawing the entire project.
(defun pl:run-needs-sync (fn)
  (and (not (equal fn 'pl:sync-drawing)) pl:*drawing-changed*))
(defun pl:cache-entities (/ all trees areas labels tables e role source pair)
  (setq all (pl:ss-list (ssget "_X" '((-3 ("PLANTCAD01"))))) pl:*link-cache* nil)
  (foreach e all
    (setq role (pl:role e))
    (cond ((equal role "TREE") (setq trees (cons e trees)))
      ((equal role "AREA") (setq areas (cons e areas)))
      ((equal role "TABLE") (setq tables (cons e tables))))
    (if (member (cdr (assoc 0 (entget e))) '("MTEXT" "MULTILEADER")) (setq labels (cons e labels)))
    (if (member role '("LABEL" "LEADER"))
      (progn
        (setq source (cdr (assoc 1005 (cdr (pl:xdata e)))) pair (assoc source pl:*link-cache*))
        (if pair (setq pl:*link-cache* (subst (cons source (cons e (cdr pair))) pair pl:*link-cache*))
          (setq pl:*link-cache* (cons (list source e) pl:*link-cache*))))))
  (setq pl:*entity-cache* (list (cons 'all all) (cons 'trees (reverse trees)) (cons 'areas (reverse areas))
    (cons 'labels (reverse labels)) (cons 'tables (reverse tables)))))
(defun pl:output-counts (scope / cached counts)
  ;; Classification/species filters change table rows, not the source statistics.
  (setq scope (list (cons 'scope (pl:get 'scope scope)) (cons 'handles (pl:get 'handles scope))))
  (if (and pl:*sync-busy* (setq cached (assoc scope pl:*count-cache*))) (cdr cached)
    (progn
      (setq counts (pl:count-rows (pl:output-table-objects scope)))
      (if pl:*sync-busy* (setq pl:*count-cache* (cons (cons scope counts) pl:*count-cache*))) counts)))
(princ)
